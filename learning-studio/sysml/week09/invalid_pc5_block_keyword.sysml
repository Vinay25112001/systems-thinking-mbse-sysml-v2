// Week 9 "predict the checker" item pc5. Predict PASS or FAIL, and the message, before you reveal the recorded result.
package PredictPc5 {
	private import ISQ::*;
	block EVTOLAircraft {
		attribute cruiseSpeed : SpeedValue;
	}
}
