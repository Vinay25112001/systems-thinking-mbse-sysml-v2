// Week 9 "predict the checker" item pc3. Predict PASS or FAIL, and the message, before you reveal the recorded result.
package PredictPc3 {
	import ISQ::*;
	import SI::*;
	part def EVTOLAircraft {
		attribute cruiseSpeed : SpeedValue = 150 [km/h];
	}
}
