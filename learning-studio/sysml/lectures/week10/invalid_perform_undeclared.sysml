// Week 10 calibration (intentionally invalid): a logical part that performs a function nobody declared (FICTIONAL).
package 'W10 Perform Undeclared' {
	part def Scheduling;
	part scheduling : Scheduling {
		perform matchRequestToAircraft;
	}
}
