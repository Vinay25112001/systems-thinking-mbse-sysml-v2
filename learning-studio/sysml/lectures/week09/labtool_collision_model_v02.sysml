// --- generated by the Week 9 lab tool: begin ---
// Riverside Food Bank Network: SysML v2 model v0.2 (Week 9: needs and requirements).
// Generated by the Week 9 lab tool on 2026-10-21 from model v0.1 (Week 8) and the Week 1 and Week 2 model inputs.
// Course conventions: every Phase I ID is a quoted short name; a need is a requirement usage with the enterprise as subject,
// framing the concerns it answers; a derivation connection runs from the parent (#original) to the child (#derive).
// A checker PASS means the file parsed, every name resolved and no validation rule fired. It does not show that a
// requirement is the right one, that its subject is the right element, or that any design meets it.
// The model v0.1 header follows.
// --- generated by the Week 9 lab tool: end ---
// Riverside Food Bank Network: SysML v2 model v0.1 (Week 8 import of the Systems Thinking package).
// Generated by the Week 8 lab tool on 2026-10-19 from Week 1 model inputs, version 3.
// Course conventions: every Phase I ID is a quoted short name <'ID'>; Context and Stakeholders are modeled now;
// every later package says which week fills it. Check this file with the course-designated checker: a PASS means it
// parsed, every name resolved and no validation rule fired. It does not show the model says what your register says.
// Dependencies: `from` names the dependent element (client), `to` the element it depends on (supplier).
package 'Riverside Food Bank Network Model' {
	doc /* Purpose: Probe of register names that collide; FICTIONAL. */
	private import ScalarValues::*;
	// --- generated by the Week 9 lab tool: begin ---
	private import ISQ::*;
	private import SI::*;
	private import ModelingMetadata::*;
	private import RequirementDerivation::*;
	private import VerificationCases::*;
	// Course convention: a need serves a mission or objective; the dependency runs from the need (client) to what it serves (supplier).
	metadata def <serves> ServesLink {
		doc /* Tags a dependency from a need (client, after from) to the mission or objective it serves (supplier, after to): a change to the objective may require a change to the need. */
		:> annotatedElement : SysML::Dependency;
	}
	// --- generated by the Week 9 lab tool: end ---
	// Course convention: the Week 1 register ratings of a stakeholder, as metadata (SysML v2 textual-notation training deck, slides 108-109).
	metadata def StakeholderAssessment {
		attribute influence : Natural;
		attribute influenceReason : String;
	}
	// Course convention: one keyword per Week 1 relationship type, restricted to dependencies (SysML v2 textual-notation training deck, slide 108); each keyword names the client's relation to the supplier.
	metadata def <conflictsWith> ConflictsWithLink {
		doc /* Tags a dependency between two stakeholders that conflict with each other. The relationship is symmetric: from and to keep the register's order, and the direction carries no meaning. */
		:> annotatedElement : SysML::Dependency;
	}
	metadata def <regulatedBy> RegulatedByLink {
		doc /* Tags a dependency between two stakeholders: the client (from) is regulated by the supplier (to), so the client depends on the supplier. The Week 1 register states it the other way round: supplier regulates client. */
		:> annotatedElement : SysML::Dependency;
	}
	metadata def <coordinatesWith> CoordinatesWithLink {
		doc /* Tags a dependency between two stakeholders that coordinate with each other. The relationship is symmetric: from and to keep the register's order, and the direction carries no meaning. */
		:> annotatedElement : SysML::Dependency;
	}
	package Context {
		doc /* The enterprise, the external systems and the operating context of the system of interest (Week 1). */
		part def <'ENT-001'> 'Riverside Food Bank Network' {
			doc /* Domain: Food security and logistics. Problem: Donated food reaches partner pantries unevenly across the county, so fresh produce runs out early while surplus spoils in store back rooms. Mission (MGO-001, modeled in Week 9): Collect surplus food from donors and deliver it safely to partner pantries across the county every week. */
			// --- generated by the Week 9 lab tool: begin ---
			// Quantities the requirements constrain (Week 9; stakeholder requirements).
			attribute daysWithProduceUntilClosingPercent : Real;
			attribute maxFoodTemperature : ThermodynamicTemperatureValue;
			attribute shortOrdersWithoutNotice : Natural;
			attribute freezerAlarmTime : DurationValue;
			attribute shiftDurationP95 : DurationValue;
			attribute quartersWithoutDistrictTable : Natural;
			// --- generated by the Week 9 lab tool: end ---
		}
		part def 'ENT-001 (EXT-001)';
		part def 'EXT-003 (EXT-002)';
		part def 'Riverside Food Bank Network (EXT-003)';
		part def 'Ångström météo 東京';
		part def 'Road network';
		part def 'Electric utility';
		part context {
			doc /* The operating context: the system of interest and 6 external system(s). */
			ref part systemOfInterest :> Physical::soi;
			part <'EXT-001'> eNT001 : 'ENT-001 (EXT-001)' { doc /* ENT-001. Kind: actor. Crosses the boundary: surplus food (in). */ }
			part <'EXT-002'> eXT003 : 'EXT-003 (EXT-002)' { doc /* EXT-003. Kind: actor. Crosses the boundary: inspection results and permits (in and out). */ }
			part <'EXT-003'> riversideFoodBankNetwork : 'Riverside Food Bank Network (EXT-003)' { doc /* Riverside Food Bank Network. Kind: actor. Crosses the boundary: food deliveries and demand reports (in and out). */ }
			part <'EXT-004'> angstromMeteo : 'Ångström météo 東京' { doc /* Ångström météo 東京. Kind: actor. Crosses the boundary: shared stock and guidance (in and out). */ }
			part <'EXT-005'> roadNetwork : 'Road network' { doc /* Road network. Kind: system. Crosses the boundary: delivery routes and travel times (in). */ }
			part <'EXT-006'> electricUtility : 'Electric utility' { doc /* Electric utility. Kind: actor. Crosses the boundary: power for cold storage (in). */ }
		}
	}
	package Stakeholders {
		doc /* Stakeholders as part definitions (the types of stakeholder parameters); concerns with a subject and stakeholders; relationships as tagged dependencies (Week 1 register). */
		part def <'STK-001'> 'STK-003 (STK-001)' {
			doc /* Role: user. Main life-cycle stage: Operation. Side: external. Approving authority: no. */
			@StakeholderAssessment { influence = 2; influenceReason = "little leverage alone, but they decide demand"; }
		}
		part def <'STK-002'> 'Stakeholders' {
			doc /* Role: authority. Main life-cycle stage: Concept. Side: external. Approving authority: yes. */
			@StakeholderAssessment { influence = 5; influenceReason = "it can suspend the food permit"; }
		}
		part def <'STK-003'> 'Grocery store donors' {
			doc /* Role: supplier. Main life-cycle stage: Operation. Side: external. Approving authority: no. */
			@StakeholderAssessment { influence = 4; influenceReason = "they decide how much is donated"; }
		}
		part def <'STK-004'> 'Result' {
			doc /* Role: user. Main life-cycle stage: Operation. Side: internal. Approving authority: no. */
			@StakeholderAssessment { influence = 3; influenceReason = "volunteer availability limits deliveries"; }
		}
		part def <'STK-005'> 'Warehouse staff' {
			doc /* Role: maintainer. Main life-cycle stage: Logistics and maintenance. Side: internal. Approving authority: no. */
			@StakeholderAssessment { influence = 2; influenceReason = "they keep storage running"; }
		}
		part def <'STK-006'> 'Funders and grant makers' {
			doc /* Role: customer. Main life-cycle stage: Concept. Side: external. Approving authority: no. */
			@StakeholderAssessment { influence = 4; influenceReason = "they fund staff and vans"; }
		}
		part def <'STK-007'> 'Neighbors of the warehouse' {
			doc /* Role: public. Main life-cycle stage: Operation. Side: external. Approving authority: no. */
			@StakeholderAssessment { influence = 2; influenceReason = "they can complain to the zoning board"; }
		}
		part def <'STK-008'> 'Waste hauler' {
			doc /* Role: supplier. Main life-cycle stage: Disposal. Side: external. Approving authority: no. */
			@StakeholderAssessment { influence = 2; influenceReason = "disposal costs rise when loads are refused"; }
		}
		concern <'CON-001'> {
			doc /* Families arriving after work find the shelves empty of fresh produce by 5 p.m. */
			subject enterprise : Context::'ENT-001';
			stakeholder sTK003 : 'STK-001';
		}
		concern <'CON-002'> {
			doc /* Cold-chain temperatures above 5 °C during delivery could make donated food unsafe to distribute. */
			subject enterprise : Context::'ENT-001';
			stakeholder stakeholders2 : 'STK-002';
		}
		concern <'CON-003'> {
			doc /* Store managers want surplus collected before closing so it does not fill their back rooms overnight. */
			subject enterprise : Context::'ENT-001';
			stakeholder groceryStoreDonors : 'STK-003';
		}
		concern <'CON-004'> {
			doc /* Volunteers drop out when delivery shifts run past the two hours they signed up for. */
			subject enterprise : Context::'ENT-001';
			stakeholder result2 : 'STK-004';
		}
		concern <'CON-005'> {
			doc /* Freezer breakdowns on weekends go unnoticed until Monday and spoil stored meat. */
			subject enterprise : Context::'ENT-001';
			stakeholder warehouseStaff : 'STK-005';
		}
		concern <'CON-006'> {
			doc /* Grant reports have to show pounds delivered per county district each quarter. */
			subject enterprise : Context::'ENT-001';
			stakeholder fundersAndGrantMakers : 'STK-006';
		}
		concern <'CON-007'> {
			doc /* Residents on Mill Street are woken by van loading before 6 a.m. */
			subject enterprise : Context::'ENT-001';
			stakeholder neighborsOfTheWarehouse : 'STK-007';
		}
		concern <'CON-008'> {
			doc /* Spoiled food mixed with packaging is refused at the composting site. */
			subject enterprise : Context::'ENT-001';
			stakeholder wasteHauler : 'STK-008';
		}
		#conflictsWith dependency <'REL-001'> from 'STK-007' to 'STK-004' {
			doc /* STK-007 conflicts with STK-004. Neighbors want no loading before 6 a.m.; volunteer drivers need early starts to finish within their shifts. */
		}
		#regulatedBy dependency <'REL-002'> from 'STK-005' to 'STK-002' {
			doc /* Register: STK-002 regulates STK-005; modeled from the dependent: STK-005 is regulated by STK-002. Food-safety inspections of the warehouse and cold storage. */
		}
		#coordinatesWith dependency <'REL-003'> from 'STK-004' to 'STK-005' {
			doc /* STK-004 coordinates with STK-005. Loading times at the warehouse dock. */
		}
	}
	package Needs {
		doc /* The mission, the objectives and the stakeholder needs as requirement usages (Week 9). A need is not a requirement on the system: it states what a stakeholder needs, in the stakeholder's words; course convention: it is modeled as a requirement usage whose subject is the enterprise, with a stakeholder parameter and a frame for each concern it answers. Capabilities follow in Week 10. */
		requirement <'MGO-001'> 'Mission' {
			doc /* Collect surplus food from donors and deliver it safely to partner pantries across the county every week. Level: mission. */
			subject enterprise : Context::'ENT-001';
		}
		requirement <'MGO-002'> {
			doc /* Keep partner pantries stocked with fresh food every week. Level: objective. */
			subject enterprise : Context::'ENT-001';
		}
		requirement <'MGO-003'> {
			doc /* Keep all donated food safe from collection to delivery. Level: objective. */
			subject enterprise : Context::'ENT-001';
		}
		requirement <'MGO-004'> {
			doc /* Run the service within what donors, volunteers and neighbors can sustain. Level: objective. */
			subject enterprise : Context::'ENT-001';
		}
		requirement <'MGO-005'> {
			doc /* Show funders how far every delivered pound reaches. Level: objective. */
			subject enterprise : Context::'ENT-001';
		}
		requirement <'NEED-001'> 'Produce until closing' {
			doc /* Families using partner pantries need the delivery service to keep fresh produce on the pantry shelves until closing time. Rationale: Families arriving after work currently find no produce left. Priority: critical. */
			subject enterprise : Context::'ENT-001';
			stakeholder familiesUsingPartnerPantries : Stakeholders::'STK-001';
			frame Stakeholders::'CON-001';
		}
		requirement <'NEED-002'> 'Safe temperatures' {
			doc /* The county health department needs the network to keep donated food within safe temperature limits throughout collection, storage and delivery. Rationale: Unsafe temperatures could make distributed food harmful. Priority: mandatory. */
			subject enterprise : Context::'ENT-001';
			stakeholder countyHealthDepartment : Stakeholders::'STK-002';
			frame Stakeholders::'CON-002';
		}
		requirement <'NEED-003'> 'Collection before closing' {
			doc /* Grocery store donors need the collection service to collect surplus food at every store before it closes for the night. Rationale: Surplus left overnight fills their storage space. Priority: desirable. */
			subject enterprise : Context::'ENT-001';
			stakeholder groceryStoreDonors : Stakeholders::'STK-003';
			frame Stakeholders::'CON-003';
		}
		requirement <'NEED-004'> 'Shifts within commitment' {
			doc /* Volunteer drivers need the delivery service to end each delivery shift within the two hours they signed up for, even when donations are heavy. Rationale: Volunteers drop out when shifts overrun their commitment. Priority: critical. */
			subject enterprise : Context::'ENT-001';
			stakeholder volunteerDrivers : Stakeholders::'STK-004';
			frame Stakeholders::'CON-004';
		}
		requirement <'NEED-005'> 'Early warning of storage failure' {
			doc /* Warehouse staff need the network to warn them of a freezer failure within minutes, at any hour including weekends. Rationale: Weekend failures currently spoil stored meat before anyone notices. Priority: critical. */
			subject enterprise : Context::'ENT-001';
			stakeholder warehouseStaff : Stakeholders::'STK-005';
			frame Stakeholders::'CON-005';
		}
		requirement <'NEED-006'> 'Reach by district' {
			doc /* Funders need the network to show how much food reached each county district during every quarter. Rationale: Grant renewals depend on evidence of reach across districts. Priority: desirable. */
			subject enterprise : Context::'ENT-001';
			stakeholder fundersAndGrantMakers : Stakeholders::'STK-006';
			frame Stakeholders::'CON-006';
		}
		requirement <'NEED-007'> 'Quiet early mornings' {
			doc /* Neighbors of the warehouse need the delivery service to keep loading noise within the limits agreed with the city, at night and early in the morning. Rationale: Early loading currently wakes residents on Mill Street. Priority: mandatory. */
			subject enterprise : Context::'ENT-001';
			stakeholder neighborsOfTheWarehouse : Stakeholders::'STK-007';
			frame Stakeholders::'CON-007';
		}
		requirement <'NEED-008'> 'Separated spoiled food' {
			doc /* The waste hauler needs the network to separate spoiled food from packaging whenever a load is handed over for composting. Rationale: Mixed loads are refused at the composting site. Priority: optional. */
			subject enterprise : Context::'ENT-001';
			stakeholder wasteHauler : Stakeholders::'STK-008';
			frame Stakeholders::'CON-008';
		}
		requirement <'NEED-009'> 'Shortfall notice' {
			doc /* Pantry coordinators need the delivery service to tell them of any shortfall in their order before the delivery leaves the warehouse. Priority: desirable. */
			subject enterprise : Context::'ENT-001';
		}
		#serves dependency 'NEED-001 serves MGO-002' from 'NEED-001' to 'MGO-002';
		#serves dependency 'NEED-002 serves MGO-003' from 'NEED-002' to 'MGO-003';
		#serves dependency 'NEED-003 serves MGO-004' from 'NEED-003' to 'MGO-004';
		#serves dependency 'NEED-004 serves MGO-004' from 'NEED-004' to 'MGO-004';
		#serves dependency 'NEED-005 serves MGO-003' from 'NEED-005' to 'MGO-003';
		#serves dependency 'NEED-006 serves MGO-005' from 'NEED-006' to 'MGO-005';
		#serves dependency 'NEED-007 serves MGO-004' from 'NEED-007' to 'MGO-004';
		#serves dependency 'NEED-008 serves MGO-003' from 'NEED-008' to 'MGO-003';
		#serves dependency 'NEED-009 serves MGO-002' from 'NEED-009' to 'MGO-002';
	}
	package Requirements {
		doc /* The stakeholder and system requirements (Week 9): each with its ID as short name, its statement as doc, a subject, a required constraint where formalized, its attributes and rationale as metadata, and a derivation connection from each parent need or requirement. Parent links to capabilities wait for Week 10, when the capabilities are modeled: REQ-STK-001 to CAP-001; REQ-STK-002 to CAP-002; REQ-STK-003 to CAP-001; REQ-STK-004 to CAP-003; REQ-STK-005 to CAP-004; REQ-STK-006 to CAP-005; REQ-SYS-002 to CAP-004. */
		// Course convention: the Week 2 requirement attributes as metadata (SysML v2 textual-notation training deck, slides 108-109).
		metadata def RequirementAttributes {
			attribute level : String;
			attribute requirementType : String;
			attribute method : VerificationMethodKind;
			attribute criterion : String;
		}
		requirement def DurationUpperLimit {
			doc /* Shared form (course convention): the measured duration shall be at most the limit. Used by REQ-SYS-001, REQ-SYS-002. */
			attribute measured : DurationValue;
			attribute limit : DurationValue;
			require constraint { measured <= limit }
		}
		requirement <'REQ-STK-001'> 'Produce until closing' {
			doc /* The delivery service shall keep fresh produce on the shelves of each partner pantry until at least 30 minutes before its closing time on every distribution day. */
			subject enterprise : Context::'ENT-001';
			attribute minDaysWithProduceUntilClosingPercent : Real = 90;
			require constraint { enterprise.daysWithProduceUntilClosingPercent >= minDaysWithProduceUntilClosingPercent }
			@RequirementAttributes { level = "stakeholder"; requirementType = "performance"; method = VerificationMethodKind::analyze; criterion = "Produce on the shelf 30 min before closing on at least 90 % of distribution days, from the pantry closing reports"; }
			@Rationale { text = "Families arriving after work currently find nothing left; the margin covers the last arrivals that coordinators report."; }
		}
		requirement <'REQ-STK-002'> 'Cold-chain limit' {
			doc /* The network shall keep donated food at or below 5 °C from collection to delivery. */
			subject enterprise : Context::'ENT-001';
			attribute maxFoodTemperatureLimit : ThermodynamicTemperatureValue = 5 ['°C'];
			require constraint { enterprise.maxFoodTemperature <= maxFoodTemperatureLimit }
			@RequirementAttributes { level = "stakeholder"; requirementType = "constraint"; method = VerificationMethodKind::test; criterion = "Logged temperature <= 5 °C for every reading of every load"; }
			@Rationale { text = "The county health department sets this limit in the food permit; an exceedance can suspend all distribution."; }
		}
		requirement <'REQ-STK-003'> 'Shortfall notice' {
			doc /* The delivery service shall notify the pantry coordinator of any shortfall in an order before the delivery leaves the warehouse. */
			subject enterprise : Context::'ENT-001';
			attribute requiredShortOrdersWithoutNotice : Natural = 0;
			require constraint { enterprise.shortOrdersWithoutNotice == requiredShortOrdersWithoutNotice }
			@RequirementAttributes { level = "stakeholder"; requirementType = "functional"; method = VerificationMethodKind::demo; criterion = "Shortfall notice received before departure in every demonstrated short order"; }
			@Rationale { text = "Coordinators plan their distribution around the delivered quantities; a late surprise leaves families without the expected items."; }
		}
		requirement <'REQ-STK-004'> 'Freezer alarm time' {
			doc /* The network shall alert the on-call warehouse staff to a freezer temperature above the alarm limit (TBD-01) within 5 minutes, at any hour. */
			subject enterprise : Context::'ENT-001';
			attribute maxFreezerAlarmTime : DurationValue = 5 [min];
			require constraint { enterprise.freezerAlarmTime <= maxFreezerAlarmTime }
			@RequirementAttributes { level = "stakeholder"; requirementType = "performance"; method = VerificationMethodKind::test; criterion = "Alarm received by the on-call phone <= 5 min after an injected rise above TBD-01, in every trial (limit pending U-001)"; }
			@Rationale { text = "Weekend failures currently spoil stored meat before anyone notices; five minutes leaves time to move stock before it warms."; }
			@StatusInfo { status = StatusKind::tbd; owner = "Warehouse manager"; }
		}
		requirement <'REQ-STK-005'> 'Shift length' {
			doc /* The delivery service shall end every volunteer delivery shift within 2 hours of its start. */
			subject enterprise : Context::'ENT-001';
			attribute maxShiftDurationP95 : DurationValue = 2 [h];
			require constraint { enterprise.shiftDurationP95 <= maxShiftDurationP95 }
			@RequirementAttributes { level = "stakeholder"; requirementType = "performance"; method = VerificationMethodKind::analyze; criterion = "Shift end minus start <= 2 h for at least 95 % of shifts in a month, from the sign-out log"; }
			@Rationale { text = "Volunteers sign up for two-hour commitments and drop out when they overrun; dispatchers plan against that commitment."; }
		}
		requirement <'REQ-STK-006'> 'Reach report to funders' {
			doc /* The network shall provide the delivered weight per county district to each funder every quarter. */
			subject enterprise : Context::'ENT-001';
			attribute requiredQuartersWithoutDistrictTable : Natural = 0;
			require constraint { enterprise.quartersWithoutDistrictTable == requiredQuartersWithoutDistrictTable }
			@RequirementAttributes { level = "stakeholder"; requirementType = "interface"; method = VerificationMethodKind::inspect; criterion = "A district-by-district weight table in each quarterly report for 4 consecutive quarters"; }
			@Rationale { text = "Grant renewals depend on evidence of reach across districts; funders compare districts to decide where to invest next."; }
		}
		requirement <'REQ-SYS-001'> 'Freezer sampling interval' : DurationUpperLimit {
			doc /* The temperature monitoring function shall sample each freezer temperature at intervals of no more than 60 s. */
			subject temperatureMonitoring : Logical::'Temperature monitoring';
			attribute :>> measured = temperatureMonitoring.sampleInterval;
			attribute :>> limit = 60 [s];
			@RequirementAttributes { level = "system"; requirementType = "performance"; method = VerificationMethodKind::test; criterion = "Interval between logged samples <= 60 s over a 24 h test"; }
			@Rationale { text = "An alert within five minutes needs several readings to confirm a rise and to filter out door openings."; }
		}
		requirement <'REQ-SYS-002'> 'Route fits the shift' : DurationUpperLimit {
			doc /* The routing tool shall plan each delivery route so that its planned duration fits within the driver's shift. */
			subject routingTool : Logical::'Routing tool';
			attribute :>> measured = routingTool.plannedRouteDuration;
			attribute :>> limit = 2 [h];
			assume constraint { doc /* The route is planned for one driver on a two-hour shift. */ }
			@RequirementAttributes { level = "system"; requirementType = "functional"; method = VerificationMethodKind::demo; criterion = "Planned duration within the shift for every route in a replayed week of orders"; }
			@Rationale { text = "Routes planned longer than the shift are the main reason shifts overrun, according to the volunteer coordinator."; }
		}
		requirement <'REQ-SYS-003'> 'Van cargo temperature' {
			doc /* The refrigerated vans shall hold their cargo at or below 5 °C for a delivery round of up to 3 hours. */
			subject systemOfInterest : Physical::'System of interest';
			attribute maxCargoTemperature : ThermodynamicTemperatureValue = 5 ['°C'];
			require constraint { systemOfInterest.cargoTemperature <= maxCargoTemperature }
			@RequirementAttributes { level = "system"; requirementType = "constraint"; method = VerificationMethodKind::test; criterion = "Cargo logger <= 5 °C for every reading over a 3 h loaded test round"; }
			@Rationale { text = "The longest round in the county takes about three hours, including loading and unloading at four pantries."; }
		}
		requirement <'REQ-SYS-004'> 'Funder report export' {
			doc /* The reporting function shall export the delivered weight per district in the funders' spreadsheet template. */
			subject reportingFunction : Logical::'Reporting function';
			attribute requiredDistrictsMissingFromExport : Natural = 0;
			require constraint { reportingFunction.districtsMissingFromExport == requiredDistrictsMissingFromExport }
			@RequirementAttributes { level = "system"; requirementType = "interface"; method = VerificationMethodKind::demo; criterion = "The export opens in the funders' template with every district filled, for one sampled quarter"; }
			@Rationale { text = "Funders compile reports from many grantees and accept only their own template; retyping by hand introduces errors."; }
		}
		requirement stakeholderRequirements {
			doc /* Specification group: the 6 stakeholder requirements. They share the enterprise as subject, so the group declares it. */
			subject enterprise : Context::'ENT-001';
			require 'REQ-STK-001';
			require 'REQ-STK-002';
			require 'REQ-STK-003';
			require 'REQ-STK-004';
			require 'REQ-STK-005';
			require 'REQ-STK-006';
		}
		requirement systemRequirements {
			doc /* Organizing group: the 4 system requirements. Each keeps its own subject, unbound to a group subject, so the group declares none and cannot be satisfied as a whole: satisfy its members. Binding each member subject to a feature of one group subject (Week 11) would make it satisfiable. */
			require 'REQ-SYS-001';
			require 'REQ-SYS-002';
			require 'REQ-SYS-003';
			require 'REQ-SYS-004';
		}
		#derivation connection 'REQ-STK-001 derives from NEED-001' {
			end #original ::> Needs::'NEED-001';
			end #derive ::> 'REQ-STK-001';
		}
		#derivation connection 'REQ-STK-002 derives from NEED-002' {
			end #original ::> Needs::'NEED-002';
			end #derive ::> 'REQ-STK-002';
		}
		#derivation connection 'REQ-STK-003 derives from NEED-009' {
			end #original ::> Needs::'NEED-009';
			end #derive ::> 'REQ-STK-003';
		}
		#derivation connection 'REQ-STK-004 derives from NEED-005' {
			end #original ::> Needs::'NEED-005';
			end #derive ::> 'REQ-STK-004';
		}
		#derivation connection 'REQ-STK-005 derives from NEED-004' {
			end #original ::> Needs::'NEED-004';
			end #derive ::> 'REQ-STK-005';
		}
		#derivation connection 'REQ-STK-006 derives from NEED-006' {
			end #original ::> Needs::'NEED-006';
			end #derive ::> 'REQ-STK-006';
		}
		#derivation connection 'REQ-SYS-001 derives from REQ-STK-004' {
			end #original ::> 'REQ-STK-004';
			end #derive ::> 'REQ-SYS-001';
		}
		#derivation connection 'REQ-SYS-002 derives from REQ-STK-005' {
			end #original ::> 'REQ-STK-005';
			end #derive ::> 'REQ-SYS-002';
		}
		#derivation connection 'REQ-SYS-003 derives from REQ-STK-002' {
			end #original ::> 'REQ-STK-002';
			end #derive ::> 'REQ-SYS-003';
		}
		#derivation connection 'REQ-SYS-004 derives from REQ-STK-006' {
			end #original ::> 'REQ-STK-006';
			end #derive ::> 'REQ-SYS-004';
		}
	}
	package Behavior {
		doc /* Week 10 models the scenarios as use cases here, with actions and states. */
	}
	package Logical {
		doc /* Week 10 models the functions and logical elements here. */
		// --- generated by the Week 9 lab tool: begin ---
		part def 'Temperature monitoring' {
			doc /* Placeholder subject of REQ-SYS-001 (Week 9). Week 10 models this element; keep the name, or update the subjects when it is renamed. */
			attribute sampleInterval : DurationValue;
		}
		part def 'Routing tool' {
			doc /* Placeholder subject of REQ-SYS-002 (Week 9). Week 10 models this element; keep the name, or update the subjects when it is renamed. */
			attribute plannedRouteDuration : DurationValue;
		}
		part def 'Reporting function' {
			doc /* Placeholder subject of REQ-SYS-004 (Week 9). Week 10 models this element; keep the name, or update the subjects when it is renamed. */
			attribute districtsMissingFromExport : Natural;
		}
		// --- generated by the Week 9 lab tool: end ---
	}
	package Physical {
		doc /* The system of interest and the elements inside its boundary (Week 1). Components, ports and interfaces follow in Week 11. */
		part def 'System of interest' { doc /* The network's collection, warehousing and delivery service that moves donated food from donors to partner pantries. */
			// --- generated by the Week 9 lab tool: begin ---
			// Quantities the requirements constrain (Week 9; system requirements).
			attribute cargoTemperature : ThermodynamicTemperatureValue;
			// --- generated by the Week 9 lab tool: end ---
		}
		part def 'System of interest (PRT-001)';
		part def 'PRT-003 (PRT-002)';
		part def 'Volunteer scheduling office';
		part def 'Donation intake desk';
		part soi : 'System of interest' {
			part <'PRT-001'> systemOfInterest : 'System of interest (PRT-001)';
			part <'PRT-002'> pRT003 : 'PRT-003 (PRT-002)';
			part <'PRT-003'> volunteerSchedulingOffice : 'Volunteer scheduling office';
			part <'PRT-004'> donationIntakeDesk : 'Donation intake desk';
		}
	}
	package Verification {
		doc /* Week 12 models the verification cases here. */
	}
	package Analysis {
		doc /* Week 13 models the technologies, the trade study and its decision here. */
	}
	package AROU {
		doc /* Week 13 models the assumptions, risks, opportunities and unknowns here. */
	}
	package Evolution {
		doc /* Week 14 models the roadmap increments here, in a form decided with the instructor. */
	}
}
