// Week 9 predict-the-checker listing (fails by design): a course ID written as an unquoted short name.
package PredictId {
	requirement <REQ-SYS-001> chargeTime {
		doc /* The charging system shall charge an aircraft to the dispatch threshold within 20 min. */
	}
}
