// --- generated by the Week 9 lab tool: begin ---
// AeroLink Urban Mobility: SysML v2 model v0.2 (Week 9: needs and requirements).
// Generated by the Week 9 lab tool from model v0.1 (Week 8) and the AeroLink Phase I package (the Week 1, 2, 3 and 5 cases).
// AeroLink Urban Mobility is FICTIONAL: every name, value and statement is a teaching value (Weeks 1-5 cases).
// Course conventions: every Phase I ID is a quoted short name; a need is a requirement usage with the enterprise as subject,
// framing the concerns it answers; a derivation connection runs from the parent (#original) to the child (#derive).
// A checker PASS means the file parsed, every name resolved and no validation rule fired. It does not show that a
// requirement is the right one, that its subject is the right element, or that any design meets it.
// The model v0.1 header follows.
// --- generated by the Week 9 lab tool: end ---
// AeroLink Urban Mobility: SysML v2 model v0.1 (Week 8 import of the Systems Thinking package).
// Generated by the Week 8 lab tool from the corrected Week 1 AeroLink case and the instructor reference baseline.
// AeroLink Urban Mobility is FICTIONAL: every name, rating and statement is a teaching value (Week 1 case).
// Course conventions: every Phase I ID is a quoted short name <'ID'>; Context and Stakeholders are modeled now;
// every later package says which week fills it. Check this file with the course-designated checker: a PASS means it
// parsed, every name resolved and no validation rule fired. It does not show the model says what your register says.
// Dependencies: `from` names the dependent element (client), `to` the element it depends on (supplier).
package 'AeroLink Model v0.2' {
	doc /* Purpose: The instructor reference model of the AeroLink enterprise (FICTIONAL). It is used by the course team to trace every later requirement, design element and verification case back to the stakeholder concern it serves, and to produce the stakeholder and concern views reviewed in Week 14. */
	private import ScalarValues::*;
	// --- generated by the Week 9 lab tool: begin ---
	private import ISQ::*;
	private import SI::*;
	private import ModelingMetadata::*;
	private import RequirementDerivation::*;
	private import VerificationCases::*;
	// Course convention: a need serves a mission or objective; the dependency runs from the need (client) to what it serves (supplier).
	metadata def <serves> ServesLink {
		doc /* Tags a dependency from a need (client, after from) to the mission or objective it serves (supplier, after to): a change to the objective may require a change to the need. */
		:> annotatedElement : SysML::Dependency;
	}
	// --- generated by the Week 9 lab tool: end ---
	// Course convention: the Week 1 register ratings of a stakeholder, as metadata (SysML v2 textual-notation training deck, slides 108-109).
	metadata def StakeholderAssessment {
		attribute interest : Natural;
		attribute influence : Natural;
		attribute influenceReason : String;
		attribute support : Natural;
		attribute supportReason : String;
	}
	// Course convention: one keyword per Week 1 relationship type, restricted to dependencies (SysML v2 textual-notation training deck, slide 108); each keyword names the client's relation to the supplier.
	metadata def <regulatedBy> RegulatedByLink {
		doc /* Tags a dependency between two stakeholders: the client (from) is regulated by the supplier (to), so the client depends on the supplier. The Week 1 register states it the other way round: supplier regulates client. */
		:> annotatedElement : SysML::Dependency;
	}
	metadata def <conflictsWith> ConflictsWithLink {
		doc /* Tags a dependency between two stakeholders that conflict with each other. The relationship is symmetric: from and to keep the register's order, and the direction carries no meaning. */
		:> annotatedElement : SysML::Dependency;
	}
	metadata def <suppliedBy> SuppliedByLink {
		doc /* Tags a dependency between two stakeholders: the client (from) is supplied by the supplier (to), so the client depends on the supplier. The Week 1 register states it the other way round: supplier supplies client. */
		:> annotatedElement : SysML::Dependency;
	}
	metadata def <fundedBy> FundedByLink {
		doc /* Tags a dependency between two stakeholders: the client (from) is funded by the supplier (to), so the client depends on the supplier. The Week 1 register states it the other way round: supplier funds client. */
		:> annotatedElement : SysML::Dependency;
	}
	metadata def <coordinatesWith> CoordinatesWithLink {
		doc /* Tags a dependency between two stakeholders that coordinate with each other. The relationship is symmetric: from and to keep the register's order, and the direction carries no meaning. */
		:> annotatedElement : SysML::Dependency;
	}
	metadata def <affectedBy> AffectedByLink {
		doc /* Tags a dependency between two stakeholders: the client (from) is affected by the supplier (to), so the client depends on the supplier. */
		:> annotatedElement : SysML::Dependency;
	}
	metadata def <partnersWith> PartnersWithLink {
		doc /* Tags a dependency between two stakeholders that partner with each other. The relationship is symmetric: from and to keep the register's order, and the direction carries no meaning. */
		:> annotatedElement : SysML::Dependency;
	}
	package Context {
		doc /* The enterprise, the external systems and the operating context of the system of interest (Week 1). */
		part def <'ENT-001'> 'AeroLink Urban Mobility' {
			doc /* Domain: Urban air mobility (FICTIONAL) Problem: Cross-town trips in the region take 45-70 minutes by road at peak hours, and no service offers a quick, predictable alternative for trips of 15-40 km (FICTIONAL, proposed). Mission (MGO-001, modeled in Week 9): Safe, quiet, on-demand air trips between six vertiports, at predictable waits and a cost that lets the network grow. */
			// --- generated by the Week 9 lab tool: begin ---
			// Quantities the requirements constrain (Week 9; stakeholder requirements).
			attribute passengerWaitP90 : DurationValue;
			attribute maxPadEdgeNoise : SoundPressureLevelValue;
			attribute dispatchesBeyondWeatherLimits : Natural;
			attribute networkCapacityTripsPerDay : Natural;
			attribute hubTurnaroundTime : DurationValue;
			attribute dispatchesWithOpenNoGoFault : Natural;
			attribute stepFreeVertiports : Natural;
			attribute responderAlertTime : DurationValue;
			attribute departuresWithoutAcceptedIntent : Natural;
			attribute peakVertiportChargingPower : PowerValue;
			attribute sensitiveHourMovementsPerPadHour : Natural;
			attribute bookingsConfirmedBeforeFullFare : Natural;
			attribute sitesWithoutLandUseApproval : Natural;
			attribute maxWalkToPublicTransport : LengthValue;
			attribute maxSimultaneousFlightsPerOperator : Natural;
			attribute flightsWithoutCompleteLogEntry : Natural;
			attribute fareRatioToRideHail : Real;
			attribute disruptionNoticeTime : DurationValue;
			attribute disruptedPassengersWithoutWayOnward : Natural;
			attribute mobilityAidsNotCarriedWithPassenger : Natural;
			attribute responderAccessClearingTime : DurationValue;
			// --- generated by the Week 9 lab tool: end ---
		}
		part def 'Controlled airspace (air traffic service)';
		part def 'Electric grid';
		part def 'Weather';
		part def 'Aircraft and spares supply';
		part def 'Public transport network';
		part def 'Emergency response service';
		part context {
			doc /* The operating context: the system of interest and 6 external system(s). */
			ref part systemOfInterest :> Physical::soi;
			part <'EXT-001'> controlledAirspaceAirTrafficService : 'Controlled airspace (air traffic service)' { doc /* Controlled airspace (air traffic service). Kind: system. Crosses the boundary: airspace access, clearances and traffic information (in and out). */ }
			part <'EXT-002'> electricGrid : 'Electric grid' { doc /* Electric grid. Kind: system. Crosses the boundary: power to the vertiport chargers (in and out). */ }
			part <'EXT-003'> weather : 'Weather' { doc /* Weather. Kind: system. Crosses the boundary: constrains operations (one-way influence) (in). */ }
			part <'EXT-004'> aircraftAndSparesSupply : 'Aircraft and spares supply' { doc /* Aircraft and spares supply. Kind: system. Crosses the boundary: aircraft and parts; delivery lead time (in and out). */ }
			part <'EXT-005'> publicTransportNetwork : 'Public transport network' { doc /* Public transport network. Kind: system. Crosses the boundary: passengers to and from vertiports (in and out). */ }
			part <'EXT-006'> emergencyResponseService : 'Emergency response service' { doc /* Emergency response service. Kind: system. Crosses the boundary: incident response at vertiports and in flight (in and out). */ }
		}
	}
	package Stakeholders {
		doc /* Stakeholders as part definitions (the types of stakeholder parameters); concerns with a subject and stakeholders; relationships as tagged dependencies (Week 1 register). */
		part def <'STK-001'> 'Passengers' {
			doc /* Role: User or operator. Main life-cycle stage: Operation. Side: external. Approving authority: no. */
			@StakeholderAssessment { interest = 5; influence = 3; influenceReason = "Revenue depends on them, but individually they have little leverage; collectively they decide demand"; support = 2; supportReason = "Curious but unconvinced until the service proves safe, quick and affordable"; }
		}
		part def <'STK-002'> 'FAA' {
			doc /* Role: Approving or regulatory authority. Main life-cycle stage: Concept. Side: external. Approving authority: yes. */
			@StakeholderAssessment { interest = 4; influence = 5; influenceReason = "Approval authority: without it no revenue operation is possible"; support = 2; supportReason = "Neutral by mandate; engaged, but commits only to evidence"; }
		}
		part def <'STK-003'> 'Investors' {
			doc /* Role: Customer, acquirer or funder. Main life-cycle stage: Concept. Side: external. Approving authority: no. */
			@StakeholderAssessment { interest = 4; influence = 5; influenceReason = "Control funding for fleet and vertiport growth"; support = 4; supportReason = "Have committed capital to the venture"; }
		}
		part def <'STK-004'> 'Communities' {
			doc /* Role: Affected public. Main life-cycle stage: Concept. Side: external. Approving authority: no. */
			@StakeholderAssessment { interest = 4; influence = 4; influenceReason = "Local opposition can block vertiport siting through planning processes"; support = 1; supportReason = "Aware of the plan; skeptical about noise near homes"; }
		}
		part def <'STK-005'> 'Vertiport operators' {
			doc /* Role: Supplier or owner of an enabling or external system. Main life-cycle stage: Operation. Side: external. Approving authority: no. */
			@StakeholderAssessment { interest = 5; influence = 4; influenceReason = "Own a scarce capacity constraint (pads, chargers)"; support = 3; supportReason = "Gain traffic from the service; want throughput protected"; }
		}
		part def <'STK-006'> 'Emergency responders' {
			doc /* Role: Supplier or owner of an enabling or external system. Main life-cycle stage: Operation. Side: external. Approving authority: no. */
			@StakeholderAssessment { interest = 3; influence = 3; influenceReason = "Must be able to respond; can impose operating conditions"; support = 2; supportReason = "Understand the plan; battery-fire procedures not yet agreed"; }
		}
		part def <'STK-007'> 'Air navigation service provider' {
			doc /* Role: Approving or regulatory authority. Main life-cycle stage: Operation. Side: external. Approving authority: no. */
			@StakeholderAssessment { interest = 4; influence = 5; influenceReason = "Controls access to airspace; capacity limits schedule density"; support = 2; supportReason = "Engaged; integration procedures still open"; }
		}
		part def <'STK-008'> 'Pilots / remote operators' {
			doc /* Role: User or operator. Main life-cycle stage: Operation. Side: internal. Approving authority: no. */
			@StakeholderAssessment { interest = 5; influence = 3; influenceReason = "Operate every flight; workforce availability limits scaling"; support = 3; supportReason = "Employees who want the service to succeed; wary of workload"; }
		}
		part def <'STK-009'> 'Maintenance technicians' {
			doc /* Role: Maintainer or support. Main life-cycle stage: Logistics and maintenance. Side: internal. Approving authority: no. */
			@StakeholderAssessment { interest = 4; influence = 2; influenceReason = "Turnaround time drives aircraft availability"; support = 3; supportReason = "Employees; support depends on release pressure staying in check"; }
		}
		part def <'STK-010'> 'Electric utility' {
			doc /* Role: Supplier or owner of an enabling or external system. Main life-cycle stage: Operation. Side: external. Approving authority: no. */
			@StakeholderAssessment { interest = 3; influence = 4; influenceReason = "Grid capacity can cap charging throughput"; support = 2; supportReason = "A new load customer; cautious about peak demand"; }
		}
		part def <'STK-011'> 'Aircraft manufacturer (OEM)' {
			doc /* Role: Supplier or owner of an enabling or external system. Main life-cycle stage: Development. Side: external. Approving authority: no. */
			@StakeholderAssessment { interest = 4; influence = 4; influenceReason = "Sole source for aircraft and parts; delivery delays shape fleet growth"; support = 4; supportReason = "AeroLink is a launch customer; committed"; }
		}
		part def <'STK-012'> 'Insurers' {
			doc /* Role: Supplier or owner of an enabling or external system. Main life-cycle stage: Operation. Side: external. Approving authority: no. */
			@StakeholderAssessment { interest = 3; influence = 4; influenceReason = "Premiums and coverage conditions constrain operations"; support = 1; supportReason = "No loss history yet; aware but uncommitted"; }
		}
		part def <'STK-013'> 'City planning authority' {
			doc /* Role: Approving or regulatory authority. Main life-cycle stage: Concept. Side: external. Approving authority: yes. */
			@StakeholderAssessment { interest = 3; influence = 5; influenceReason = "Grants or blocks vertiport sites"; support = 1; supportReason = "Aware of the proposal; awaiting site applications and consultation"; }
		}
		part def <'STK-014'> 'Accessibility advocates' {
			doc /* Role: Affected public. Main life-cycle stage: Concept. Side: external. Approving authority: no. */
			@StakeholderAssessment { interest = 3; influence = 2; influenceReason = "Shape public acceptance and legal compliance expectations"; support = 1; supportReason = "Aware; not yet consulted on boarding design"; }
		}
		part def <'STK-015'> 'Passengers with reduced mobility' {
			doc /* Role: User or operator. Main life-cycle stage: Operation. Side: external. Approving authority: no. */
			@StakeholderAssessment { interest = 5; influence = 2; influenceReason = "Individually little leverage; accessibility expectations and their advocates amplify it"; support = 1; supportReason = "Not yet consulted; will judge the service by whether boarding works for them"; }
		}
		concern <'CON-001'> 'Predictable waiting time' {
			doc /* Passengers judge the service by how long they wait between confirming a ride and boarding, and by whether that wait is predictable. */
			subject enterprise : Context::'ENT-001';
			stakeholder passengers : 'STK-001';
		}
		concern <'CON-002'> 'Personal safety in flight' {
			doc /* Passengers must be confident that every flight is safe before they will use a new mode of transport. */
			subject enterprise : Context::'ENT-001';
			stakeholder passengers : 'STK-001';
		}
		concern <'CON-003'> 'Affordable fare' {
			doc /* Passengers compare the fare with ride-hail and public transport for the same trip. */
			subject enterprise : Context::'ENT-001';
			stakeholder passengers : 'STK-001';
		}
		concern <'CON-004'> 'Airworthiness and operational safety' {
			doc /* The FAA is concerned that aircraft and operations stay within approved safety limits at all times, including in adverse weather. */
			subject enterprise : Context::'ENT-001';
			stakeholder fAA : 'STK-002';
		}
		concern <'CON-005'> 'Return on capital and path to scale' {
			doc /* Investors are concerned that capital spent on aircraft and vertiports produces capacity that is actually used. */
			subject enterprise : Context::'ENT-001';
			stakeholder investors : 'STK-003';
		}
		concern <'CON-006'> 'Pad throughput and charging capacity' {
			doc /* Vertiport operators are concerned that charging and turnaround, not demand, limit how many flights a pad can handle. */
			subject enterprise : Context::'ENT-001';
			stakeholder vertiportOperators : 'STK-005';
		}
		concern <'CON-007'> 'Battery-fire response at vertiports' {
			doc /* Emergency responders are concerned about early warning, access and procedures for a lithium battery fire on a pad. */
			subject enterprise : Context::'ENT-001';
			stakeholder emergencyResponders : 'STK-006';
		}
		concern <'CON-008'> 'Airspace integration' {
			doc /* The air navigation service provider is concerned that air-taxi traffic is known and separated from other airspace users. */
			subject enterprise : Context::'ENT-001';
			stakeholder airNavigationServiceProvider : 'STK-007';
		}
		concern <'CON-009'> 'Operator workload and automation trust' {
			doc /* Pilots and remote operators are concerned about workload, duty time and how far they can trust automated decision aids. */
			subject enterprise : Context::'ENT-001';
			stakeholder pilotsRemoteOperators : 'STK-008';
		}
		concern <'CON-010'> 'Turnaround pressure on maintenance' {
			doc /* Maintenance technicians are concerned that schedule pressure leads to aircraft being released without a clear condition picture. */
			subject enterprise : Context::'ENT-001';
			stakeholder maintenanceTechnicians : 'STK-009';
		}
		concern <'CON-011'> 'Peak grid load' {
			doc /* The electric utility is concerned about simultaneous high-power charging exceeding the agreed connection capacity at a vertiport. */
			subject enterprise : Context::'ENT-001';
			stakeholder electricUtility : 'STK-010';
		}
		concern <'CON-012'> 'Community noise' {
			doc /* Residents near vertiports are concerned about take-off and landing noise, how often it occurs and at what hours. */
			subject enterprise : Context::'ENT-001';
			stakeholder communities : 'STK-004';
		}
		concern <'CON-013'> 'Step-free boarding access' {
			doc /* Accessibility advocates are concerned that passengers using wheelchairs can board and alight without being lifted. */
			subject enterprise : Context::'ENT-001';
			stakeholder accessibilityAdvocates : 'STK-014';
		}
		concern <'CON-014'> 'Quantifiable operational risk' {
			doc /* Insurers are concerned that operational risk is measured and recorded so that premiums can be set on evidence. */
			subject enterprise : Context::'ENT-001';
			stakeholder insurers : 'STK-012';
		}
		concern <'CON-015'> 'Fleet orders and delivery milestones' {
			doc /* The aircraft manufacturer is concerned that AeroLink's aircraft orders, delivery slots and payment milestones are kept as agreed in the purchase agreement, because they set its own production plan. */
			subject enterprise : Context::'ENT-001';
			stakeholder aircraftManufacturerOEM : 'STK-011';
		}
		concern <'CON-016'> 'Land use and zoning of vertiport sites' {
			doc /* The city planning authority is concerned that vertiport sites conform to zoning and land-use plans and connect to public transport, especially sites in residential districts. */
			subject enterprise : Context::'ENT-001';
			stakeholder cityPlanningAuthority : 'STK-013';
		}
		concern <'CON-017'> 'Travel with one\'s own mobility aid' {
			doc /* Passengers with reduced mobility are concerned that they can board, travel and alight without being lifted and without being parted from their wheelchair or other mobility aid. */
			subject enterprise : Context::'ENT-001';
			stakeholder passengersWithReducedMobility : 'STK-015';
		}
		#regulatedBy dependency <'REL-001'> from 'STK-011' to 'STK-002' {
			doc /* Register: STK-002 regulates STK-011; modeled from the dependent: STK-011 is regulated by STK-002. Aircraft certification. */
		}
		#conflictsWith dependency <'REL-002'> from 'STK-004' to 'STK-005' {
			doc /* STK-004 conflicts with STK-005. Noise and siting vs throughput. */
		}
		#suppliedBy dependency <'REL-003'> from 'STK-005' to 'STK-010' {
			doc /* Register: STK-010 supplies STK-005; modeled from the dependent: STK-005 is supplied by STK-010. Grid power for charging. */
		}
		#fundedBy dependency <'REL-004'> from 'STK-011' to 'STK-003' {
			doc /* Register: STK-003 funds STK-011; modeled from the dependent: STK-011 is funded by STK-003. Fleet purchase financing. */
		}
		#coordinatesWith dependency <'REL-005'> from 'STK-006' to 'STK-005' {
			doc /* STK-006 coordinates with STK-005. Incident response plans. */
		}
		#coordinatesWith dependency <'REL-006'> from 'STK-007' to 'STK-008' {
			doc /* STK-007 coordinates with STK-008. Flight clearances. */
		}
		#affectedBy dependency <'REL-007'> from 'STK-013' to 'STK-004' {
			doc /* STK-013 is affected by STK-004. Public consultation on siting. */
		}
		#partnersWith dependency <'REL-008'> from 'STK-012' to 'STK-003' {
			doc /* STK-012 partners with STK-003. Risk transfer conditions on financing. */
		}
	}
	package Needs {
		doc /* The mission, the objectives and the stakeholder needs as requirement usages (Week 9). A need is not a requirement on the system: it states what a stakeholder needs, in the stakeholder's words; course convention: it is modeled as a requirement usage whose subject is the enterprise, with a stakeholder parameter and a frame for each concern it answers. Capabilities follow in Week 10. */
		requirement <'MGO-001'> 'Mission' {
			doc /* Safe, quiet, on-demand air trips between six vertiports, at predictable waits and a cost that lets the network grow. Level: mission. */
			subject enterprise : Context::'ENT-001';
		}
		requirement <'MGO-002'> 'Goal: Short, predictable waits' {
			doc /* Short, predictable waits. Level: goal. */
			subject enterprise : Context::'ENT-001';
		}
		requirement <'MGO-003'> 'Goal: Be a good neighbor' {
			doc /* Be a good neighbor. Level: goal. */
			subject enterprise : Context::'ENT-001';
		}
		requirement <'MGO-004'> 'Goal: Grow capacity in step with demand' {
			doc /* Grow capacity in step with demand. Level: goal. */
			subject enterprise : Context::'ENT-001';
		}
		requirement <'MGO-009'> 'Goal: Every flight within approved limits' {
			doc /* Every flight within approved limits. Level: goal. */
			subject enterprise : Context::'ENT-001';
		}
		requirement <'MGO-005'> '90 % boarded within 15 min' {
			doc /* From month 6 onward, at least 90 % of passengers in each calendar month board within 15 min of confirming their ride. Level: objective. */
			subject enterprise : Context::'ENT-001';
		}
		requirement <'MGO-006'> 'No pad-edge noise exceedance' {
			doc /* Zero take-off or landing events above 65 dBA at any vertiport pad edge in each quarter. The objective also counts pad-hours before 07:00 and after 20:00 above the agreed evening and early-morning event cap (TBD-03); the target is zero such pad-hours per quarter, alongside zero events above 65 dBA. Level: objective. */
			subject enterprise : Context::'ENT-001';
		}
		requirement <'MGO-007'> 'Year-2 capacity with headroom' {
			doc /* By month 24, serve the planning demand of 240 trips/day at a fleet utilization of no more than 80 %, that is, provide at least 300 trips/day of capacity. Level: objective. */
			subject enterprise : Context::'ENT-001';
		}
		requirement <'MGO-008'> 'Zero dispatches outside limits' {
			doc /* Zero flights dispatched outside the approved weather, energy-reserve or airworthiness limits in each quarter. Level: objective. */
			subject enterprise : Context::'ENT-001';
		}
		#derivation connection 'MGO-005 derives from MGO-002' {
			end #original ::> 'MGO-002';
			end #derive ::> 'MGO-005';
		}
		#derivation connection 'MGO-006 derives from MGO-003' {
			end #original ::> 'MGO-003';
			end #derive ::> 'MGO-006';
		}
		#derivation connection 'MGO-007 derives from MGO-004' {
			end #original ::> 'MGO-004';
			end #derive ::> 'MGO-007';
		}
		#derivation connection 'MGO-008 derives from MGO-009' {
			end #original ::> 'MGO-009';
			end #derive ::> 'MGO-008';
		}
		requirement <'NEED-001'> 'Short, predictable wait to board' {
			doc /* Passengers need the air-taxi service to let them board within a short and predictable time after they confirm a ride. Condition: Throughout the 16 h operating day, including peak hours. Rationale: The wait and its predictability decide whether passengers use the service again. Priority: critical. */
			subject enterprise : Context::'ENT-001';
			stakeholder passengers : Stakeholders::'STK-001';
			frame Stakeholders::'CON-001';
		}
		requirement <'NEED-002'> 'Assurance of flight within safety limits' {
			doc /* The FAA needs the air-taxi service to demonstrate that every flight is conducted within the approved airworthiness, energy-reserve and weather limits. Condition: For every flight, including when weather changes during the day. Rationale: The regulator must be assured that the operation, not only the aircraft, stays inside the approved envelope; the same assurance answers the passengers' safety concern. Priority: mandatory. */
			subject enterprise : Context::'ENT-001';
			stakeholder fAA : Stakeholders::'STK-002';
			stakeholder passengers : Stakeholders::'STK-001';
			frame Stakeholders::'CON-004';
			frame Stakeholders::'CON-002';
		}
		requirement <'NEED-003'> 'Noise exposure within the local agreement' {
			doc /* Communities near vertiports need the air-taxi service to keep take-off and landing noise exposure at nearby homes within the agreed limits on the loudness of each event and on the number of events in the evening and early morning. Condition: At every vertiport, every operating day; the evening and early-morning hours are the noise-sensitive period. Rationale: Residents judge noise by how loud each event is and by how often it happens when they rest; exceeding either agreed limit puts the site permit at risk and erodes acceptance. Priority: mandatory. */
			subject enterprise : Context::'ENT-001';
			stakeholder communities : Stakeholders::'STK-004';
			frame Stakeholders::'CON-012';
		}
		requirement <'NEED-004'> 'Pads not limited by turnaround' {
			doc /* Vertiport operators need the air-taxi service to turn arriving aircraft around quickly enough that pad occupancy does not become the limit on departures. Condition: At every vertiport during peak hours. Rationale: How long an arriving aircraft occupies a pad sets how many departures the pad can support. Priority: critical. */
			subject enterprise : Context::'ENT-001';
			stakeholder vertiportOperators : Stakeholders::'STK-005';
			frame Stakeholders::'CON-006';
		}
		requirement <'NEED-005'> 'Capacity that grows with demand' {
			doc /* Investors need the air-taxi service to grow its capacity in step with demand. Condition: Throughout the first three years of service, while demand grows. Rationale: Capital that is short when demand arrives, or idle when it does not, erodes the return investors expect. Priority: desirable. */
			subject enterprise : Context::'ENT-001';
			stakeholder investors : Stakeholders::'STK-003';
			frame Stakeholders::'CON-005';
		}
		requirement <'NEED-006'> 'Early warning and access for a vertiport fire' {
			doc /* Emergency responders need the air-taxi service to give them early warning of, and safe access to, a battery fire at a vertiport. Condition: At any hour of operation, at every vertiport. Rationale: Lithium battery fires escalate within minutes and need specialist equipment and a safe approach; warning without access leaves the response half defined. Priority: mandatory. */
			subject enterprise : Context::'ENT-001';
			stakeholder emergencyResponders : Stakeholders::'STK-006';
			frame Stakeholders::'CON-007';
		}
		requirement <'NEED-007'> 'Known aircraft condition before release' {
			doc /* Maintenance technicians need the air-taxi service to make the condition of each aircraft known before the aircraft is released for flight. Condition: At every release, regardless of schedule pressure. Rationale: Releasing an aircraft whose condition is unknown is the failure technicians most want to prevent. Priority: mandatory. */
			subject enterprise : Context::'ENT-001';
			stakeholder maintenanceTechnicians : Stakeholders::'STK-009';
			frame Stakeholders::'CON-010';
		}
		requirement <'NEED-008'> 'Unassisted step-free travel' {
			doc /* Passengers with reduced mobility need the air-taxi service to let them board, travel and alight without being lifted or separated from their mobility aid. Condition: At every vertiport, throughout operating hours. Rationale: Being lifted is unsafe and undignified and excludes passengers who travel with their own mobility aid; the accessibility advocates raised the same concern on their behalf. Priority: critical. */
			subject enterprise : Context::'ENT-001';
			stakeholder passengersWithReducedMobility : Stakeholders::'STK-015';
			stakeholder accessibilityAdvocates : Stakeholders::'STK-014';
			frame Stakeholders::'CON-017';
			frame Stakeholders::'CON-013';
		}
		requirement <'NEED-009'> 'Flight intent known to the ANSP' {
			doc /* The air navigation service provider needs the air-taxi service to make each flight's intended route and time known before the aircraft enters controlled airspace. Condition: Whenever a flight will enter controlled airspace. Rationale: The ANSP can separate air-taxi flights from other traffic only if it knows them in advance. Priority: mandatory. */
			subject enterprise : Context::'ENT-001';
			stakeholder airNavigationServiceProvider : Stakeholders::'STK-007';
			frame Stakeholders::'CON-008';
		}
		requirement <'NEED-010'> 'Charging load within the grid connection' {
			doc /* The electric utility needs the air-taxi service to keep the power drawn at each vertiport within the agreed connection capacity. Condition: At all times, including when several arriving aircraft charge together. Rationale: Exceeding the agreed connection trips protection or incurs penalty tariffs. Priority: mandatory. */
			subject enterprise : Context::'ENT-001';
			stakeholder electricUtility : Stakeholders::'STK-010';
			frame Stakeholders::'CON-011';
		}
		requirement <'NEED-011'> 'Prompt notice and a way onward when a trip is disrupted' {
			doc /* Passengers need the air-taxi service to tell them promptly when a confirmed trip is held, diverted or cancelled, and to offer them a usable way to complete the journey. Condition: Whenever a confirmed trip is held, diverted or cancelled, including during weather holds and region-wide suspensions. Rationale: A passenger left waiting without news or a way onward loses more time and trust than one told early and offered an alternative (exposed by scenario SCN-005). Notice and a way onward are one end-to-end outcome: notice alone leaves the passenger stranded. Priority: desirable. */
			subject enterprise : Context::'ENT-001';
			stakeholder passengers : Stakeholders::'STK-001';
			frame Stakeholders::'CON-001';
		}
		requirement <'NEED-012'> 'Sites that conform to the land-use plan' {
			doc /* The city planning authority needs the air-taxi service to operate only from vertiport sites that conform to the zoning and land-use plan. Condition: For every site, from site approval through operation. Rationale: The authority grants or blocks sites; a site that breaches the land-use plan cannot be approved. Priority: mandatory. */
			subject enterprise : Context::'ENT-001';
			stakeholder cityPlanningAuthority : Stakeholders::'STK-013';
			frame Stakeholders::'CON-016';
		}
		requirement <'NEED-013'> 'Manageable operator workload' {
			doc /* Pilots and remote operators need the air-taxi service to keep their workload manageable throughout every duty period. Condition: Throughout every duty period, including weather disruptions (SCN-005) and other off-nominal events. Rationale: Overload erodes safety margins and caps how many flights each operator can handle; workforce availability limits scaling. Priority: critical. */
			subject enterprise : Context::'ENT-001';
			stakeholder pilotsRemoteOperators : Stakeholders::'STK-008';
			frame Stakeholders::'CON-009';
		}
		requirement <'NEED-014'> 'Operational risk measurable from evidence' {
			doc /* Insurers need the air-taxi service to make its operational risk measurable from evidence recorded on every flight. Condition: On every flight, from the first day of service. Rationale: Premiums and coverage are set on evidence; without an incident and loss record insurers price the unknown and constrain operations. Priority: desirable. */
			subject enterprise : Context::'ENT-001';
			stakeholder insurers : Stakeholders::'STK-012';
			frame Stakeholders::'CON-014';
		}
		requirement <'NEED-015'> 'Full fare known before booking' {
			doc /* Passengers need the air-taxi service to show them the full fare before they confirm a trip. Condition: At every booking, including at peak hours. Rationale: Passengers compare the fare with the alternatives before they commit; a fare revealed late loses the booking and the passenger's trust. Priority: desirable. */
			subject enterprise : Context::'ENT-001';
			stakeholder passengers : Stakeholders::'STK-001';
			frame Stakeholders::'CON-003';
		}
		requirement <'NEED-016'> 'Sites connected to public transport' {
			doc /* The city planning authority needs the air-taxi service to operate only from vertiport sites that connect with the public transport network. Condition: For every site, from site approval through operation, especially sites in residential districts. Rationale: A site that strands passengers away from public transport adds road traffic around it and weakens the case for approval. Priority: critical. */
			subject enterprise : Context::'ENT-001';
			stakeholder cityPlanningAuthority : Stakeholders::'STK-013';
			frame Stakeholders::'CON-016';
		}
		requirement <'NEED-017'> 'Fares competitive with ground alternatives' {
			doc /* Passengers need the air-taxi service to offer fares that are competitive with ride-hail and public transport for the same journey. Condition: For typical trips between any two vertiports, including at peak hours. Rationale: Passengers choose by comparing the fare with ride-hail and public transport for the same trip; a fare far above both loses the trip. Priority: desirable. */
			subject enterprise : Context::'ENT-001';
			stakeholder passengers : Stakeholders::'STK-001';
			frame Stakeholders::'CON-003';
		}
		#serves dependency 'NEED-001 serves MGO-002' from 'NEED-001' to 'MGO-002';
		#serves dependency 'NEED-002 serves MGO-009' from 'NEED-002' to 'MGO-009';
		#serves dependency 'NEED-003 serves MGO-003' from 'NEED-003' to 'MGO-003';
		#serves dependency 'NEED-004 serves MGO-002' from 'NEED-004' to 'MGO-002';
		#serves dependency 'NEED-005 serves MGO-004' from 'NEED-005' to 'MGO-004';
		#serves dependency 'NEED-006 serves MGO-001' from 'NEED-006' to 'MGO-001';
		#serves dependency 'NEED-007 serves MGO-009' from 'NEED-007' to 'MGO-009';
		#serves dependency 'NEED-008 serves MGO-001' from 'NEED-008' to 'MGO-001';
		#serves dependency 'NEED-009 serves MGO-001' from 'NEED-009' to 'MGO-001';
		#serves dependency 'NEED-010 serves MGO-004' from 'NEED-010' to 'MGO-004';
		#serves dependency 'NEED-011 serves MGO-002' from 'NEED-011' to 'MGO-002';
		#serves dependency 'NEED-012 serves MGO-003' from 'NEED-012' to 'MGO-003';
		#serves dependency 'NEED-013 serves MGO-009' from 'NEED-013' to 'MGO-009';
		#serves dependency 'NEED-014 serves MGO-004' from 'NEED-014' to 'MGO-004';
		#serves dependency 'NEED-015 serves MGO-001' from 'NEED-015' to 'MGO-001';
		#serves dependency 'NEED-016 serves MGO-003' from 'NEED-016' to 'MGO-003';
		#serves dependency 'NEED-017 serves MGO-001' from 'NEED-017' to 'MGO-001';
	}
	package Requirements {
		doc /* The stakeholder and system requirements (Week 9): each with its ID as short name, its statement as doc, a subject, a required constraint where formalized, its attributes and rationale as metadata, and a derivation connection from each parent need or requirement. Parent links to capabilities wait for Week 10, when the capabilities are modeled: REQ-STK-001 to CAP-001; REQ-STK-002 to CAP-007; REQ-STK-003 to CAP-005; REQ-STK-004 to CAP-008; REQ-STK-005 to CAP-003; REQ-STK-006 to CAP-006; REQ-STK-007 to CAP-001; REQ-STK-008 to CAP-009; REQ-STK-009 to CAP-004; REQ-STK-010 to CAP-010; REQ-STK-011 to CAP-007; REQ-STK-012 to CAP-014; REQ-STK-013 to CAP-011; REQ-STK-014 to CAP-011; REQ-STK-015 to CAP-012; REQ-STK-016 to CAP-013; REQ-STK-017 to CAP-014; REQ-STK-018 to CAP-015; REQ-STK-019 to CAP-015; REQ-STK-020 to CAP-001; REQ-STK-021 to CAP-009; REQ-SYS-003 to CAP-004; REQ-SYS-005 to CAP-002. */
		// Course convention: the Week 2 requirement attributes as metadata (SysML v2 textual-notation training deck, slides 108-109).
		metadata def RequirementAttributes {
			attribute level : String;
			attribute requirementType : String;
			attribute method : VerificationMethodKind;
			attribute criterion : String;
		}
		requirement def DurationUpperLimit {
			doc /* Shared form (course convention): the measured duration shall be at most the limit. Used by REQ-SYS-005, REQ-SYS-008, REQ-SYS-009. */
			attribute measured : DurationValue;
			attribute limit : DurationValue;
			require constraint { measured <= limit }
		}
		requirement <'REQ-STK-001'> 'Passenger wait to board' {
			doc /* The AeroLink service shall board at least 90 % of passengers in each calendar month within 15 min of their ride confirmation. */
			subject enterprise : Context::'ENT-001';
			attribute maxPassengerWaitP90 : DurationValue = 15 [min];
			require constraint { enterprise.passengerWaitP90 <= maxPassengerWaitP90 }
			@RequirementAttributes { level = "stakeholder"; requirementType = "performance"; method = VerificationMethodKind::analyze; criterion = "90th-percentile confirmation-to-boarding time <= 15 min per calendar month"; }
			@Rationale { text = "Attraction to the service halves at a 15 min wait (A-001); controlling the 90th percentile protects the passengers most likely to stop using the service, not just the average."; }
		}
		requirement <'REQ-STK-002'> 'Pad-edge noise limit' {
			doc /* The AeroLink service shall keep every take-off and landing at or below 65 dBA LAmax at the pad edge of each vertiport. */
			subject enterprise : Context::'ENT-001';
			attribute maxPadEdgeNoiseLimit : SoundPressureLevelValue = 65 [dB];
			require constraint { enterprise.maxPadEdgeNoise <= maxPadEdgeNoiseLimit }
			@RequirementAttributes { level = "stakeholder"; requirementType = "constraint"; method = VerificationMethodKind::test; criterion = "LAmax <= 65 dBA at the pad edge for every movement"; }
			@Rationale { text = "The 65 dBA limit is the local agreement with the city; an exceedance puts the operating permit of the vertiport at risk."; }
		}
		requirement <'REQ-STK-003'> 'No dispatch outside weather limits' {
			doc /* The AeroLink service shall not dispatch a flight when the forecast at its departure or arrival vertiport exceeds the approved aircraft weather limits (TBD-01). */
			subject enterprise : Context::'ENT-001';
			attribute requiredDispatchesBeyondWeatherLimits : Natural = 0;
			require constraint { enterprise.dispatchesBeyondWeatherLimits == requiredDispatchesBeyondWeatherLimits }
			@RequirementAttributes { level = "stakeholder"; requirementType = "functional"; method = VerificationMethodKind::demo; criterion = "Zero dispatches with a forecast beyond TBD-01 at either end (limits pending U-001)"; }
			@Rationale { text = "Weather beyond the approved limits removes the margin the certification basis assumes; the FAA needs assurance that the operation, not just the aircraft, respects those limits."; }
			@StatusInfo { status = StatusKind::tbd; owner = "Director of Flight Operations"; }
		}
		requirement <'REQ-STK-004'> 'Network capacity by month 24' {
			doc /* The AeroLink service shall provide a capacity of at least 300 trips per day across the six-vertiport network within the 16 h operating day by month 24. */
			subject enterprise : Context::'ENT-001';
			attribute minNetworkCapacityTripsPerDay : Natural = 300;
			require constraint { enterprise.networkCapacityTripsPerDay >= minNetworkCapacityTripsPerDay }
			@RequirementAttributes { level = "stakeholder"; requirementType = "performance"; method = VerificationMethodKind::analyze; criterion = "Network capacity >= 300 trips/day by month 24"; }
			@Rationale { text = "Serving the 240 trips/day planning demand at no more than 80 % utilization keeps the queue-driven wait near 10 min (Week 1 dynamics model); 240 / 0.8 = 300."; }
		}
		requirement <'REQ-STK-005'> 'Hub turnaround time' {
			doc /* The AeroLink service shall return an aircraft arriving at a hub vertiport to dispatch-ready status within 25 min of its arrival on the pad. */
			subject enterprise : Context::'ENT-001';
			attribute maxHubTurnaroundTime : DurationValue = 25 [min];
			require constraint { enterprise.hubTurnaroundTime <= maxHubTurnaroundTime }
			@RequirementAttributes { level = "stakeholder"; requirementType = "performance"; method = VerificationMethodKind::test; criterion = "Pad arrival to dispatch-ready <= 25 min"; }
			@Rationale { text = "Turnaround time sets how many departures a pad can support; 25 min is the 20 min Data Sheet charge plus 5 min for rotor stop, safety check, connection and disconnection, with deplaning and boarding overlapping the charge."; }
		}
		requirement <'REQ-STK-006'> 'No dispatch with an open no-go fault' {
			doc /* The AeroLink service shall confirm that an aircraft has no open no-go fault before each dispatch. */
			subject enterprise : Context::'ENT-001';
			attribute requiredDispatchesWithOpenNoGoFault : Natural = 0;
			require constraint { enterprise.dispatchesWithOpenNoGoFault == requiredDispatchesWithOpenNoGoFault }
			@RequirementAttributes { level = "stakeholder"; requirementType = "functional"; method = VerificationMethodKind::demo; criterion = "Dispatch blocked in 100 % of demonstrated cases with an open no-go fault"; }
			@Rationale { text = "Technicians need the aircraft condition to be known before release whatever the schedule pressure; a dispatch interlock removes the judgment call from the turnaround."; }
		}
		requirement <'REQ-STK-007'> 'Step-free boarding' {
			doc /* The AeroLink service shall allow a passenger with reduced mobility to board and alight at every vertiport without being lifted. */
			subject enterprise : Context::'ENT-001';
			attribute minStepFreeVertiports : Natural = 6;
			require constraint { enterprise.stepFreeVertiports >= minStepFreeVertiports }
			@RequirementAttributes { level = "stakeholder"; requirementType = "constraint"; method = VerificationMethodKind::inspect; criterion = "Step-free route from terminal to cabin at all 6 vertiports"; }
			@Rationale { text = "Lifting a passenger is unsafe and undignified and excludes passengers who travel with their own mobility aid."; }
		}
		requirement <'REQ-STK-008'> 'Responder alert time' {
			doc /* The AeroLink service shall alert emergency responders to a battery fire on a vertiport pad within 60 s of detection. */
			subject enterprise : Context::'ENT-001';
			attribute maxResponderAlertTime : DurationValue = 60 [s];
			require constraint { enterprise.responderAlertTime <= maxResponderAlertTime }
			@RequirementAttributes { level = "stakeholder"; requirementType = "performance"; method = VerificationMethodKind::test; criterion = "Detection-to-responder-alert <= 60 s"; }
			@Rationale { text = "Lithium battery fires escalate within minutes; an early alert lets responders arrive with the right equipment."; }
		}
		requirement <'REQ-STK-009'> 'Flight intent to the air traffic service' {
			doc /* The AeroLink service shall provide each flight's intended route and departure time to the air navigation service provider before take-off. */
			subject enterprise : Context::'ENT-001';
			attribute requiredDeparturesWithoutAcceptedIntent : Natural = 0;
			require constraint { enterprise.departuresWithoutAcceptedIntent == requiredDeparturesWithoutAcceptedIntent }
			@RequirementAttributes { level = "stakeholder"; requirementType = "interface"; method = VerificationMethodKind::demo; criterion = "Intent accepted by the ANSP for 100 % of demonstrated departures before take-off"; }
			@Rationale { text = "The ANSP must know each flight before it enters controlled airspace to separate it from other traffic."; }
		}
		requirement <'REQ-STK-010'> 'Vertiport power within the grid connection' {
			doc /* The AeroLink service shall keep the total charging power drawn at each vertiport within the connection capacity agreed with the utility (TBD-02 kW). */
			subject enterprise : Context::'ENT-001';
			attribute maxPeakVertiportChargingPower : PowerValue { doc /* TBD-02: value pending (owner: Vertiport Infrastructure Manager). */ }
			require constraint { enterprise.peakVertiportChargingPower <= maxPeakVertiportChargingPower }
			@RequirementAttributes { level = "stakeholder"; requirementType = "constraint"; method = VerificationMethodKind::test; criterion = "Peak vertiport charging power <= TBD-02 kW (pending U-002)"; }
			@Rationale { text = "Exceeding the agreed connection trips protection or incurs penalty tariffs and erodes the relationship with the utility."; }
			@StatusInfo { status = StatusKind::tbd; owner = "Vertiport Infrastructure Manager"; }
		}
		requirement <'REQ-STK-011'> 'Evening and early-morning event cap' {
			doc /* The AeroLink service shall limit take-offs and landings at each vertiport pad before 07:00 and after 20:00 to no more than the hourly number agreed with the city (TBD-03). */
			subject enterprise : Context::'ENT-001';
			attribute maxSensitiveHourMovementsPerPadHour : Natural { doc /* TBD-03: value pending (owner: Head of Community Relations). */ }
			require constraint { enterprise.sensitiveHourMovementsPerPadHour <= maxSensitiveHourMovementsPerPadHour }
			@RequirementAttributes { level = "stakeholder"; requirementType = "constraint"; method = VerificationMethodKind::analyze; criterion = "Movements per pad per hour before 07:00 and after 20:00 <= TBD-03, from the movement log, every operating day (cap pending U-003)"; }
			@Rationale { text = "The corrected NEED-003 bounds how often residents are disturbed in the hours they rest as well as how loud each event is; REQ-STK-002 covers only the loudness. The cap is the shared variable of the REL-002 conflict with throughput, so it must be a number before the Week 3 trade can be run."; }
			@StatusInfo { status = StatusKind::tbd; owner = "Head of Community Relations"; }
		}
		requirement <'REQ-STK-012'> 'Full fare before confirmation' {
			doc /* The AeroLink service shall show the passenger the full fare for the requested trip, including every charge, before the passenger confirms the booking. */
			subject enterprise : Context::'ENT-001';
			attribute requiredBookingsConfirmedBeforeFullFare : Natural = 0;
			require constraint { enterprise.bookingsConfirmedBeforeFullFare == requiredBookingsConfirmedBeforeFullFare }
			@RequirementAttributes { level = "stakeholder"; requirementType = "functional"; method = VerificationMethodKind::demo; criterion = "Full fare displayed before the confirmation step in 100 % of demonstrated bookings, peak and off-peak"; }
			@Rationale { text = "Passengers compare the fare with the alternatives before they commit (NEED-015); a charge revealed after confirmation loses the booking and the passenger's trust."; }
		}
		requirement <'REQ-STK-013'> 'Sites with land-use approval' {
			doc /* The AeroLink service shall operate only from vertiport sites that hold a land-use approval from the city planning authority. */
			subject enterprise : Context::'ENT-001';
			attribute requiredSitesWithoutLandUseApproval : Natural = 0;
			require constraint { enterprise.sitesWithoutLandUseApproval == requiredSitesWithoutLandUseApproval }
			@RequirementAttributes { level = "stakeholder"; requirementType = "constraint"; method = VerificationMethodKind::inspect; criterion = "A current land-use approval on file for each of the 6 sites before its first revenue flight"; }
			@Rationale { text = "The city planning authority grants or blocks sites; a site that breaches the land-use plan cannot be approved (NEED-012)."; }
		}
		requirement <'REQ-STK-014'> 'Sites linked to public transport' {
			doc /* The AeroLink service shall operate only from vertiport sites within 400 m (TBR-01) walking distance of a public transport stop. */
			subject enterprise : Context::'ENT-001';
			attribute maxWalkToPublicTransportLimit : LengthValue = 400 [m];
			require constraint { enterprise.maxWalkToPublicTransport <= maxWalkToPublicTransportLimit }
			@RequirementAttributes { level = "stakeholder"; requirementType = "constraint"; method = VerificationMethodKind::inspect; criterion = "Measured walking route <= 400 m from each site to a public transport stop (value TBR-01, U-005)"; }
			@Rationale { text = "The city weighs public-transport access in approving a site (NEED-016). The 400 m is a known value with low confidence: it is marked TBR-01, tracked by U-005, until the city confirms the distance it applies."; }
			@StatusInfo { status = StatusKind::tbc; owner = "Head of Partnerships"; }
		}
		requirement <'REQ-STK-015'> 'Simultaneous flights per remote operator' {
			doc /* The AeroLink service shall assign no more than TBD-04 simultaneous flights to one remote operator, including during weather disruptions. */
			subject enterprise : Context::'ENT-001';
			attribute maxSimultaneousFlightsPerOperatorLimit : Natural { doc /* TBD-04: value pending (owner: Director of Flight Operations). */ }
			require constraint { enterprise.maxSimultaneousFlightsPerOperator <= maxSimultaneousFlightsPerOperatorLimit }
			@RequirementAttributes { level = "stakeholder"; requirementType = "performance"; method = VerificationMethodKind::analyze; criterion = "Maximum simultaneous flights per operator <= TBD-04 in every duty period, including replayed disruption days (limit pending U-004)"; }
			@Rationale { text = "Overload erodes safety margins (NEED-013); SCN-005 showed that a disruption loads the operators, but nothing in the flows limits their workload. The limit is unknown until the Week 3 workload analysis."; }
			@StatusInfo { status = StatusKind::tbd; owner = "Director of Flight Operations"; }
		}
		requirement <'REQ-STK-016'> 'Auditable record of every flight' {
			doc /* The AeroLink service shall record the flight data, incidents and maintenance actions of every flight in a log that its insurers can audit. */
			subject enterprise : Context::'ENT-001';
			attribute requiredFlightsWithoutCompleteLogEntry : Natural = 0;
			require constraint { enterprise.flightsWithoutCompleteLogEntry == requiredFlightsWithoutCompleteLogEntry }
			@RequirementAttributes { level = "stakeholder"; requirementType = "functional"; method = VerificationMethodKind::inspect; criterion = "A complete log entry for 100 % of flights in a sampled month, readable by the insurers' auditor"; }
			@Rationale { text = "Insurers set premiums on evidence (NEED-014); a record kept from the first day of service gives them a loss history instead of an unknown."; }
		}
		requirement <'REQ-STK-017'> 'Fare competitive with ground alternatives' {
			doc /* The AeroLink service shall offer each trip between two vertiports at a fare no more than 2.0 times (TBR-02) the ride-hail fare for the same journey at the same time. */
			subject enterprise : Context::'ENT-001';
			attribute maxFareRatioToRideHail : Real = 2.0;
			require constraint { enterprise.fareRatioToRideHail <= maxFareRatioToRideHail }
			@RequirementAttributes { level = "stakeholder"; requirementType = "constraint"; method = VerificationMethodKind::analyze; criterion = "Monthly fare survey: AeroLink fare ÷ ride-hail fare <= 2.0 for the sampled journeys (ratio TBR-02, U-006)"; }
			@Rationale { text = "Passengers choose by comparing fares (NEED-017). The ratio is the marketing team's first estimate, marked TBR-02 and tracked by U-006 until the Week 3 trade relates fare to demand."; }
			@StatusInfo { status = StatusKind::tbc; owner = "Head of Customer Experience"; }
		}
		requirement <'REQ-STK-018'> 'Notice of a disrupted trip' {
			doc /* The AeroLink service shall notify each passenger whose confirmed trip is held, diverted or cancelled within TBD-05 min of the disruption decision. */
			subject enterprise : Context::'ENT-001';
			attribute maxDisruptionNoticeTime : DurationValue { doc /* TBD-05: value pending (owner: Head of Customer Experience). */ }
			require constraint { enterprise.disruptionNoticeTime <= maxDisruptionNoticeTime }
			@RequirementAttributes { level = "stakeholder"; requirementType = "performance"; method = VerificationMethodKind::demo; criterion = "In replayed disruption days, every affected passenger notified within TBD-05 min of the decision (notice time pending U-007)"; }
			@Rationale { text = "Closes, with REQ-STK-019, the Week 2 trace-audit gap for NEED-011 as its disposition asked. The notice time is unknown, so it carries an owned TBD (U-007) rather than an invented number."; }
			@StatusInfo { status = StatusKind::tbd; owner = "Head of Customer Experience"; }
		}
		requirement <'REQ-STK-019'> 'A way onward for a disrupted trip' {
			doc /* The AeroLink service shall offer each passenger whose confirmed trip is held, diverted or cancelled a way onward to the destination. */
			subject enterprise : Context::'ENT-001';
			attribute requiredDisruptedPassengersWithoutWayOnward : Natural = 0;
			require constraint { enterprise.disruptedPassengersWithoutWayOnward == requiredDisruptedPassengersWithoutWayOnward }
			@RequirementAttributes { level = "stakeholder"; requirementType = "functional"; method = VerificationMethodKind::demo; criterion = "In replayed disruption days, every affected passenger offered a booked way onward (a later flight or the public-transport fallback) before leaving the vertiport"; }
			@Rationale { text = "Closes, with REQ-STK-018, the Week 2 trace-audit gap for NEED-011: a notice without a way onward still strands the passenger. The way onward rests on the public-transport fallback (A-008)."; }
		}
		requirement <'REQ-STK-020'> 'Mobility aid travels with its passenger' {
			doc /* The AeroLink service shall carry each passenger's wheelchair or other mobility aid on the same flight as the passenger and return it to the passenger at the cabin door on arrival. */
			subject enterprise : Context::'ENT-001';
			attribute requiredMobilityAidsNotCarriedWithPassenger : Natural = 0;
			require constraint { enterprise.mobilityAidsNotCarriedWithPassenger == requiredMobilityAidsNotCarriedWithPassenger }
			@RequirementAttributes { level = "stakeholder"; requirementType = "functional"; method = VerificationMethodKind::demo; criterion = "In demonstrated trips from every vertiport, 100 % of mobility aids travel on their passenger's flight and are returned at the cabin door"; }
			@Rationale { text = "Closes the Week 2 open item for NEED-008, which the Week 7 review deferred to Week 9: REQ-STK-007 lets the passenger board and alight without being lifted, but nothing kept the passenger with their mobility aid during the trip."; }
		}
		requirement <'REQ-STK-021'> 'Responder access to a pad' {
			doc /* The AeroLink service shall clear an access route for emergency responders to any vertiport pad within TBD-08 min of a battery-fire alarm. */
			subject enterprise : Context::'ENT-001';
			attribute maxResponderAccessClearingTime : DurationValue { doc /* TBD-08: value pending (owner: Vertiport Infrastructure Manager). */ }
			require constraint { enterprise.responderAccessClearingTime <= maxResponderAccessClearingTime }
			@RequirementAttributes { level = "stakeholder"; requirementType = "performance"; method = VerificationMethodKind::demo; criterion = "Access route clear within TBD-08 min of the alarm in every demonstrated drill at every vertiport (time pending U-010)"; }
			@Rationale { text = "Closes the Week 2 open item for NEED-006, which the Week 7 review deferred to Week 9: REQ-STK-008 alerts the responders, but nothing gave them safe access to the pad. The clearing time is not agreed with the emergency services, so it carries an owned TBD (U-010) rather than an invented number."; }
			@StatusInfo { status = StatusKind::tbd; owner = "Vertiport Infrastructure Manager"; }
		}
		requirement <'REQ-SYS-001'> 'Charge to dispatch threshold in 20 min' {
			doc /* The charging system shall charge an aircraft from any landing state of charge at or above the 20 % reserve to the dispatch threshold within 20 min. */
			subject chargers : Physical::'Chargers';
			attribute maxChargeTimeToDispatch : DurationValue = 20 [min];
			require constraint { chargers.chargeTimeToDispatch <= maxChargeTimeToDispatch }
			@RequirementAttributes { level = "system"; requirementType = "performance"; method = VerificationMethodKind::test; criterion = "Charge time from 20 % reserve to dispatch threshold <= 20 min"; }
			@Rationale { text = "The worst planned arrival state is the 20 % reserve that every flight plan protects (REQ-SYS-003); meeting 20 min from that state keeps the 25 min hub turnaround of REQ-STK-005 achievable."; }
		}
		requirement <'REQ-SYS-002'> 'Aircraft pad-edge noise' {
			doc /* The eVTOL aircraft shall produce no more than 65 dBA LAmax at the pad edge during take-off and landing on the published vertiport procedures. */
			subject aircraft : Physical::'Aircraft';
			attribute maxPadEdgeNoise : SoundPressureLevelValue = 65 [dB];
			require constraint { aircraft.padEdgeNoise <= maxPadEdgeNoise }
			@RequirementAttributes { level = "system"; requirementType = "performance"; method = VerificationMethodKind::test; criterion = "LAmax <= 65 dBA at the pad edge, every measured movement"; }
			@Rationale { text = "The aircraft is the noise source; allocating the whole community limit to it keeps the vertiport free of noise-abatement infrastructure."; }
		}
		requirement <'REQ-SYS-003'> 'Planned landing energy reserve' {
			doc /* The flight planning function shall plan every flight so that the aircraft lands with at least 20 % of its usable battery energy remaining. */
			subject flightOperations : Logical::'Flight Operations';
			attribute minPlannedLandingEnergyPercent : Real = 20;
			require constraint { flightOperations.plannedLandingEnergyPercent >= minPlannedLandingEnergyPercent }
			@RequirementAttributes { level = "system"; requirementType = "performance"; method = VerificationMethodKind::analyze; criterion = "Planned landing energy >= 20 % of usable energy, every flight plan"; }
			@Rationale { text = "The 20 % reserve covers a hold or a diversion in SCN-002 A1 and SCN-005 A1. It derives directly from CAP-004 because no stakeholder requirement carries the energy-planning obligation."; }
		}
		requirement <'REQ-SYS-004'> 'Weather dispatch hold' {
			doc /* The operations system shall place a dispatch hold on any vertiport whose forecast wind, gust or visibility within the next 30 min is outside the aircraft limits (TBD-01). */
			subject opsCenter : Physical::'Ops center';
			attribute requiredMissedWeatherHolds : Natural = 0;
			require constraint { opsCenter.missedWeatherHolds == requiredMissedWeatherHolds }
			@RequirementAttributes { level = "system"; requirementType = "functional"; method = VerificationMethodKind::demo; criterion = "Hold placed for every injected forecast outside TBD-01 (pending U-001)"; }
			@Rationale { text = "A vertiport-level hold implements REQ-STK-003 before a flight is dispatched, rather than relying on each operator's judgment."; }
			@StatusInfo { status = StatusKind::tbd; owner = "Director of Flight Operations"; }
		}
		requirement <'REQ-SYS-005'> 'Aircraft assignment time' : DurationUpperLimit {
			doc /* The scheduling function shall assign a dispatch-ready aircraft to at least 99 % of confirmed ride requests within 60 s of confirmation. */
			subject scheduling : Logical::'Scheduling';
			attribute :>> measured = scheduling.assignmentLatencyP99;
			attribute :>> limit = 60 [s];
			@RequirementAttributes { level = "system"; requirementType = "performance"; method = VerificationMethodKind::test; criterion = "Confirmation-to-assignment <= 60 s for at least 99 % of at least 200 requests in a replayed peak-hour request profile"; }
			@Rationale { text = "Assignment must be a negligible part of the 15 min wait budget (REQ-STK-001) so that the remaining time is set by aircraft and charger availability."; }
		}
		requirement <'REQ-SYS-006'> 'Fleet availability' {
			doc /* The fleet shall achieve an availability of at least 90 % of scheduled aircraft-hours in each calendar month. */
			subject fleetManagement : Logical::'Fleet Management';
			attribute minFleetAvailabilityPercent : Real = 90;
			require constraint { fleetManagement.fleetAvailabilityPercent >= minFleetAvailabilityPercent }
			@RequirementAttributes { level = "system"; requirementType = "performance"; method = VerificationMethodKind::analyze; criterion = "Available aircraft-hours ÷ scheduled aircraft-hours >= 90 % per month"; }
			@Rationale { text = "The planning rate of 20 trips per aircraft per day assumes 90 % availability (43 min cycle); lower availability removes capacity needed for REQ-STK-004."; }
		}
		requirement <'REQ-SYS-007'> 'Block time for the design trip' {
			doc /* The eVTOL aircraft shall complete a 25 km vertiport-to-vertiport trip within 16 min block time in still air. */
			subject aircraft : Physical::'Aircraft';
			attribute maxStillAirDesignTripBlockTime : DurationValue = 16 [min];
			require constraint { aircraft.stillAirDesignTripBlockTime <= maxStillAirDesignTripBlockTime }
			@RequirementAttributes { level = "system"; requirementType = "performance"; method = VerificationMethodKind::test; criterion = "Block time <= 16 min for a 25 km trip, still air"; }
			@Rationale { text = "Block time drives the 43 min aircraft cycle and therefore the capacity of REQ-STK-004 (10 min cruise plus 6 min terminal phases; cycle = 16 min block + 25 min turnaround + 2 min positioning)."; }
		}
		requirement <'REQ-SYS-008'> 'No-go fault flag time' : DurationUpperLimit {
			doc /* The maintenance management function shall mark an aircraft unavailable for dispatch within 2 min of a no-go fault being reported. */
			subject maintenanceManagement : Logical::'Maintenance Management';
			attribute :>> measured = maintenanceManagement.noGoFlagLatency;
			attribute :>> limit = 2 [min];
			@RequirementAttributes { level = "system"; requirementType = "performance"; method = VerificationMethodKind::test; criterion = "Fault report to unavailable status <= 2 min"; }
			@Rationale { text = "Release follows boarding and the pre-departure check, at least 5 min after assignment, so a 2 min flag removes a faulted aircraft from the pool before it can be released."; }
		}
		requirement <'REQ-SYS-009'> 'Fire alarm transmission' : DurationUpperLimit {
			doc /* The vertiport fire detection system shall transmit a battery-fire alarm to the emergency services dispatch center within 30 s of detection. */
			subject fireAlarm : Physical::'Fire alarm';
			attribute :>> measured = fireAlarm.alarmTransmissionTime;
			attribute :>> limit = 30 [s];
			@RequirementAttributes { level = "system"; requirementType = "interface"; method = VerificationMethodKind::test; criterion = "Detection to receipt at the dispatch center <= 30 s"; }
			@Rationale { text = "Transmission takes half of the 60 s alert budget of REQ-STK-008, leaving the rest for the dispatch center to alert crews."; }
		}
		requirement <'REQ-SYS-010'> 'Vertiport charging power limit' {
			doc /* The charging system shall limit the combined power of all chargers at a vertiport to the configured connection limit (TBD-02 kW). */
			subject chargers : Physical::'Chargers';
			attribute maxCombinedChargerPower : PowerValue { doc /* TBD-02: value pending (owner: Vertiport Infrastructure Manager). */ }
			require constraint { chargers.combinedChargerPower <= maxCombinedChargerPower }
			@RequirementAttributes { level = "system"; requirementType = "constraint"; method = VerificationMethodKind::test; criterion = "Combined charger power <= configured limit under every tested load case (limit pending U-002)"; }
			@Rationale { text = "Enforcing the limit in the charging system, not by procedure, keeps REQ-STK-010 met when several aircraft arrive together."; }
			@StatusInfo { status = StatusKind::tbd; owner = "Vertiport Infrastructure Manager"; }
		}
		requirement <'REQ-SYS-011'> 'Sensitive-hour movement limit' {
			doc /* The scheduling function shall schedule no take-off or landing at a vertiport pad before 07:00 or after 20:00 beyond the hourly movement limit configured for that pad (TBD-03). */
			subject scheduling : Logical::'Scheduling';
			attribute requiredMovementsScheduledBeyondLimit : Natural = 0;
			require constraint { scheduling.movementsScheduledBeyondLimit == requiredMovementsScheduledBeyondLimit }
			@RequirementAttributes { level = "system"; requirementType = "functional"; method = VerificationMethodKind::test; criterion = "In a replayed evening schedule, zero movements scheduled beyond the configured limit at any pad in any sensitive hour (limit pending U-003)"; }
			@Rationale { text = "The event cap of REQ-STK-011 is met where departures are planned, not by asking pilots to count; scheduling is the function that decides how many movements each pad gets per hour."; }
			@StatusInfo { status = StatusKind::tbd; owner = "Head of Community Relations"; }
		}
		requirement <'REQ-SYS-012'> 'Fare shown before confirmation' {
			doc /* The booking function shall display the total fare, including every charge, before it accepts a booking confirmation. */
			subject customerServices : Logical::'Customer Services';
			attribute requiredConfirmationsAcceptedBeforeFareShown : Natural = 0;
			require constraint { customerServices.confirmationsAcceptedBeforeFareShown == requiredConfirmationsAcceptedBeforeFareShown }
			@RequirementAttributes { level = "system"; requirementType = "functional"; method = VerificationMethodKind::demo; criterion = "Total fare displayed before the confirmation is accepted, in 100 % of demonstrated booking paths"; }
			@Rationale { text = "Allocates REQ-STK-012 to the booking function: whichever channel a passenger uses, the fare is complete before the commitment."; }
		}
		requirement <'REQ-SYS-013'> 'Flight intent filed before departure' {
			doc /* The operations system shall send each flight intent to the air navigation service provider over IF-003 at least 10 min before the planned departure. */
			subject opsCenter : Physical::'Ops center';
			attribute minIntentLeadTime : DurationValue = 10 [min];
			require constraint { opsCenter.intentLeadTime >= minIntentLeadTime }
			@RequirementAttributes { level = "system"; requirementType = "interface"; method = VerificationMethodKind::demo; criterion = "Intent received by the air navigation service provider at least 10 min before departure for 100 % of demonstrated departures"; }
			@Rationale { text = "Refines REQ-STK-009 into the interface exchange: the 10 min lead lets the provider accept or amend the intent before the aircraft is released. The value is a proposed planning figure to agree with the provider."; }
		}
		requirement <'REQ-SYS-014'> 'Weather forecast refresh' {
			doc /* The operations system shall receive a forecast covering at least the next 60 min for every vertiport from the weather information service over IF-011 at least every 10 min. */
			subject opsCenter : Physical::'Ops center';
			attribute maxForecastRefreshInterval : DurationValue = 10 [min];
			require constraint { opsCenter.forecastRefreshInterval <= maxForecastRefreshInterval }
			@RequirementAttributes { level = "system"; requirementType = "performance"; method = VerificationMethodKind::test; criterion = "Interval between received forecasts at most 10 min, and every forecast covering at least 60 min ahead, at every vertiport over a replayed 16 h operating day"; }
			@Rationale { text = "The dispatch hold of REQ-SYS-004 looks 30 min ahead, so the newest forecast must always cover the next 30 min. A forecast covering 60 min and refreshed every 10 min still covers 60 − 10 = 50 min ahead just before the next one arrives; it stops covering the 30 min look-ahead only when it is 30 min old, so two consecutive lost refreshes are tolerated before the hold. The horizon and the interval are proposed for agreement with the provider."; }
		}
		requirement <'REQ-SYS-015'> 'Pad incident records to the evidence log' {
			doc /* The pad fire detection system shall send each pad incident record to the operations center evidence log over IF-015 within 1 h of the incident. */
			subject fireAlarm : Physical::'Fire alarm';
			attribute maxIncidentRecordDelay : DurationValue = 1 [h];
			require constraint { fireAlarm.incidentRecordDelay <= maxIncidentRecordDelay }
			@RequirementAttributes { level = "system"; requirementType = "performance"; method = VerificationMethodKind::test; criterion = "Every injected pad incident present in the evidence log within 1 h, in a test of at least 20 incidents"; }
			@Rationale { text = "Refines REQ-STK-016, whose auditable record of every flight had no path for pad incidents (the Week 4 finding). One hour keeps the log complete for the next shift's review; the value is proposed."; }
		}
		requirement stakeholderRequirements {
			doc /* Specification group: the 21 stakeholder requirements. They share the enterprise as subject, so the group declares it. */
			subject enterprise : Context::'ENT-001';
			require 'REQ-STK-001';
			require 'REQ-STK-002';
			require 'REQ-STK-003';
			require 'REQ-STK-004';
			require 'REQ-STK-005';
			require 'REQ-STK-006';
			require 'REQ-STK-007';
			require 'REQ-STK-008';
			require 'REQ-STK-009';
			require 'REQ-STK-010';
			require 'REQ-STK-011';
			require 'REQ-STK-012';
			require 'REQ-STK-013';
			require 'REQ-STK-014';
			require 'REQ-STK-015';
			require 'REQ-STK-016';
			require 'REQ-STK-017';
			require 'REQ-STK-018';
			require 'REQ-STK-019';
			require 'REQ-STK-020';
			require 'REQ-STK-021';
		}
		requirement systemRequirements {
			doc /* Organizing group: the 15 system requirements. Each keeps its own subject, unbound to a group subject, so the group declares none and cannot be satisfied as a whole: satisfy its members. Binding each member subject to a feature of one group subject (Week 11) would make it satisfiable. */
			require 'REQ-SYS-001';
			require 'REQ-SYS-002';
			require 'REQ-SYS-003';
			require 'REQ-SYS-004';
			require 'REQ-SYS-005';
			require 'REQ-SYS-006';
			require 'REQ-SYS-007';
			require 'REQ-SYS-008';
			require 'REQ-SYS-009';
			require 'REQ-SYS-010';
			require 'REQ-SYS-011';
			require 'REQ-SYS-012';
			require 'REQ-SYS-013';
			require 'REQ-SYS-014';
			require 'REQ-SYS-015';
		}
		#derivation connection 'REQ-STK-001 derives from NEED-001' {
			end #original ::> Needs::'NEED-001';
			end #derive ::> 'REQ-STK-001';
		}
		#derivation connection 'REQ-STK-002 derives from NEED-003' {
			end #original ::> Needs::'NEED-003';
			end #derive ::> 'REQ-STK-002';
		}
		#derivation connection 'REQ-STK-003 derives from NEED-002' {
			end #original ::> Needs::'NEED-002';
			end #derive ::> 'REQ-STK-003';
		}
		#derivation connection 'REQ-STK-004 derives from NEED-005' {
			end #original ::> Needs::'NEED-005';
			end #derive ::> 'REQ-STK-004';
		}
		#derivation connection 'REQ-STK-005 derives from NEED-004' {
			end #original ::> Needs::'NEED-004';
			end #derive ::> 'REQ-STK-005';
		}
		#derivation connection 'REQ-STK-006 derives from NEED-007' {
			end #original ::> Needs::'NEED-007';
			end #derive ::> 'REQ-STK-006';
		}
		#derivation connection 'REQ-STK-007 derives from NEED-008' {
			end #original ::> Needs::'NEED-008';
			end #derive ::> 'REQ-STK-007';
		}
		#derivation connection 'REQ-STK-008 derives from NEED-006' {
			end #original ::> Needs::'NEED-006';
			end #derive ::> 'REQ-STK-008';
		}
		#derivation connection 'REQ-STK-009 derives from NEED-009' {
			end #original ::> Needs::'NEED-009';
			end #derive ::> 'REQ-STK-009';
		}
		#derivation connection 'REQ-STK-010 derives from NEED-010' {
			end #original ::> Needs::'NEED-010';
			end #derive ::> 'REQ-STK-010';
		}
		#derivation connection 'REQ-STK-011 derives from NEED-003' {
			end #original ::> Needs::'NEED-003';
			end #derive ::> 'REQ-STK-011';
		}
		#derivation connection 'REQ-STK-012 derives from NEED-015' {
			end #original ::> Needs::'NEED-015';
			end #derive ::> 'REQ-STK-012';
		}
		#derivation connection 'REQ-STK-013 derives from NEED-012' {
			end #original ::> Needs::'NEED-012';
			end #derive ::> 'REQ-STK-013';
		}
		#derivation connection 'REQ-STK-014 derives from NEED-016' {
			end #original ::> Needs::'NEED-016';
			end #derive ::> 'REQ-STK-014';
		}
		#derivation connection 'REQ-STK-015 derives from NEED-013' {
			end #original ::> Needs::'NEED-013';
			end #derive ::> 'REQ-STK-015';
		}
		#derivation connection 'REQ-STK-016 derives from NEED-014' {
			end #original ::> Needs::'NEED-014';
			end #derive ::> 'REQ-STK-016';
		}
		#derivation connection 'REQ-STK-017 derives from NEED-017' {
			end #original ::> Needs::'NEED-017';
			end #derive ::> 'REQ-STK-017';
		}
		#derivation connection 'REQ-STK-018 derives from NEED-011' {
			end #original ::> Needs::'NEED-011';
			end #derive ::> 'REQ-STK-018';
		}
		#derivation connection 'REQ-STK-019 derives from NEED-011' {
			end #original ::> Needs::'NEED-011';
			end #derive ::> 'REQ-STK-019';
		}
		#derivation connection 'REQ-STK-020 derives from NEED-008' {
			end #original ::> Needs::'NEED-008';
			end #derive ::> 'REQ-STK-020';
		}
		#derivation connection 'REQ-STK-021 derives from NEED-006' {
			end #original ::> Needs::'NEED-006';
			end #derive ::> 'REQ-STK-021';
		}
		#derivation connection 'REQ-SYS-001 derives from REQ-STK-005' {
			end #original ::> 'REQ-STK-005';
			end #derive ::> 'REQ-SYS-001';
		}
		#derivation connection 'REQ-SYS-002 derives from REQ-STK-002' {
			end #original ::> 'REQ-STK-002';
			end #derive ::> 'REQ-SYS-002';
		}
		#derivation connection 'REQ-SYS-004 derives from REQ-STK-003' {
			end #original ::> 'REQ-STK-003';
			end #derive ::> 'REQ-SYS-004';
		}
		#derivation connection 'REQ-SYS-005 derives from REQ-STK-001' {
			end #original ::> 'REQ-STK-001';
			end #derive ::> 'REQ-SYS-005';
		}
		#derivation connection 'REQ-SYS-006 derives from REQ-STK-004' {
			end #original ::> 'REQ-STK-004';
			end #derive ::> 'REQ-SYS-006';
		}
		#derivation connection 'REQ-SYS-007 derives from REQ-STK-004' {
			end #original ::> 'REQ-STK-004';
			end #derive ::> 'REQ-SYS-007';
		}
		#derivation connection 'REQ-SYS-008 derives from REQ-STK-006' {
			end #original ::> 'REQ-STK-006';
			end #derive ::> 'REQ-SYS-008';
		}
		#derivation connection 'REQ-SYS-009 derives from REQ-STK-008' {
			end #original ::> 'REQ-STK-008';
			end #derive ::> 'REQ-SYS-009';
		}
		#derivation connection 'REQ-SYS-010 derives from REQ-STK-010' {
			end #original ::> 'REQ-STK-010';
			end #derive ::> 'REQ-SYS-010';
		}
		#derivation connection 'REQ-SYS-011 derives from REQ-STK-011' {
			end #original ::> 'REQ-STK-011';
			end #derive ::> 'REQ-SYS-011';
		}
		#derivation connection 'REQ-SYS-012 derives from REQ-STK-012' {
			end #original ::> 'REQ-STK-012';
			end #derive ::> 'REQ-SYS-012';
		}
		#derivation connection 'REQ-SYS-013 derives from REQ-STK-009' {
			end #original ::> 'REQ-STK-009';
			end #derive ::> 'REQ-SYS-013';
		}
		#derivation connection 'REQ-SYS-014 derives from REQ-STK-003' {
			end #original ::> 'REQ-STK-003';
			end #derive ::> 'REQ-SYS-014';
		}
		#derivation connection 'REQ-SYS-015 derives from REQ-STK-016' {
			end #original ::> 'REQ-STK-016';
			end #derive ::> 'REQ-SYS-015';
		}
	}
	package Behavior {
		doc /* Mapped in Week 8, modeled later: Operational scenario SCN-001 to SCN-005 (Week 10: use case with actors). */
	}
	package Logical {
		doc /* Week 10 models the functions and logical elements here. */
		// --- generated by the Week 9 lab tool: begin ---
		part def 'Flight Operations' {
			doc /* Placeholder subject of REQ-SYS-003 (Week 9). Week 10 models this element; keep the name, or update the subjects when it is renamed. */
			attribute plannedLandingEnergyPercent : Real;
		}
		part def 'Scheduling' {
			doc /* Placeholder subject of REQ-SYS-005, REQ-SYS-011 (Week 9). Week 10 models this element; keep the name, or update the subjects when it is renamed. */
			attribute assignmentLatencyP99 : DurationValue;
			attribute movementsScheduledBeyondLimit : Natural;
		}
		part def 'Fleet Management' {
			doc /* Placeholder subject of REQ-SYS-006 (Week 9). Week 10 models this element; keep the name, or update the subjects when it is renamed. */
			attribute fleetAvailabilityPercent : Real;
		}
		part def 'Maintenance Management' {
			doc /* Placeholder subject of REQ-SYS-008 (Week 9). Week 10 models this element; keep the name, or update the subjects when it is renamed. */
			attribute noGoFlagLatency : DurationValue;
		}
		part def 'Customer Services' {
			doc /* Placeholder subject of REQ-SYS-012 (Week 9). Week 10 models this element; keep the name, or update the subjects when it is renamed. */
			attribute confirmationsAcceptedBeforeFareShown : Natural;
		}
		// --- generated by the Week 9 lab tool: end ---
	}
	package Physical {
		doc /* The system of interest and the elements inside its boundary (Week 1). Components, ports and interfaces follow in Week 11. */
		part def 'System of interest' { doc /* the AeroLink air-taxi service: The system of interest inside the enterprise. AeroLink controls the fleet, the operations center, and booking and dispatch: the narrower system of interest. The service also needs elements AeroLink does not control, the vertiport operators' pads and chargers and the passenger demand they serve, so SOI-001 is drawn at the wider system of interest, which SEBoK permits for a service. */ }
		part soi : 'System of interest';
		// --- generated by the Week 9 lab tool: begin ---
		part def 'Chargers' {
			doc /* Placeholder subject of REQ-SYS-001, REQ-SYS-010 (Week 9). Week 11 models this element; keep the name, or update the subjects when it is renamed. */
			attribute chargeTimeToDispatch : DurationValue;
			attribute combinedChargerPower : PowerValue;
		}
		part def 'Aircraft' {
			doc /* Placeholder subject of REQ-SYS-002, REQ-SYS-007 (Week 9). Week 11 models this element; keep the name, or update the subjects when it is renamed. */
			attribute padEdgeNoise : SoundPressureLevelValue;
			attribute stillAirDesignTripBlockTime : DurationValue;
		}
		part def 'Ops center' {
			doc /* Placeholder subject of REQ-SYS-004, REQ-SYS-013, REQ-SYS-014 (Week 9). Week 11 models this element; keep the name, or update the subjects when it is renamed. */
			attribute missedWeatherHolds : Natural;
			attribute intentLeadTime : DurationValue;
			attribute forecastRefreshInterval : DurationValue;
		}
		part def 'Fire alarm' {
			doc /* Placeholder subject of REQ-SYS-009, REQ-SYS-015 (Week 9). Week 11 models this element; keep the name, or update the subjects when it is renamed. */
			attribute alarmTransmissionTime : DurationValue;
			attribute incidentRecordDelay : DurationValue;
		}
		// --- generated by the Week 9 lab tool: end ---
	}
	package Verification {
		doc /* Week 12 models the verification cases here. */
	}
	package Analysis {
		doc /* Week 13 models the technologies, the trade study and its decision here. */
	}
	package AROU {
		doc /* Mapped in Week 8, modeled later: Assumption A-001 to A-008 (Week 13: metadata annotation); Unknown (TBD/TBR) U-001, U-002 (Week 13: metadata annotation). */
	}
	package Evolution {
		doc /* Week 14 models the roadmap increments here, in a form decided with the instructor. */
	}
}
