// --- generated by the Week 11 lab tool: begin ---
// O'Neil "Quick" Relief \ Network */ Co: SysML v2 model v0.4 (Week 11: physical architecture and interfaces).
// Generated by the Week 11 lab tool on 2026-10-22 from model v0.3 (Week 10) and the Week 5 model inputs.
// Course conventions: a physical part performs the functions placed on it; a logical part is allocated to each physical
// part that performs one of its functions; one port definition per interface, end B using its conjugate.
// A checker PASS means the file parsed, every name resolved and no validation rule fired. It does not show that
// connected ports match, that a flow runs the right way, or that a satisfy claim is true.
// The model v0.3 header follows.
// --- generated by the Week 11 lab tool: end ---
// --- generated by the Week 10 lab tool: begin ---
// O'Neil "Quick" Relief \ Network */ Co: SysML v2 model v0.3 (Week 10: logical architecture and behavior).
// Generated by the Week 10 lab tool on 2026-10-22 from model v0.2 (Week 9) and the Week 2 and Week 4 model inputs.
// Course conventions: a capability is an action definition and a function an action usage; a logical part performs the
// functions allocated to it; a requirement is allocated to a function; a scenario step subsets its function.
// A checker PASS means the file parsed, every name resolved and no validation rule fired. It does not show that a
// flow follows the ConOps, that a guard means its condition, or that the states are complete.
// The model v0.2 header follows.
// --- generated by the Week 10 lab tool: end ---
// --- generated by the Week 9 lab tool: begin ---
// O'Neil "Quick" Relief \ Network */ Co: SysML v2 model v0.2 (Week 9: needs and requirements).
// Generated by the Week 9 lab tool on 2026-10-21 from model v0.1 (Week 8) and the Week 1 and Week 2 model inputs.
// Course conventions: every Phase I ID is a quoted short name; a need is a requirement usage with the enterprise as subject,
// framing the concerns it answers; a derivation connection runs from the parent (#original) to the child (#derive).
// A checker PASS means the file parsed, every name resolved and no validation rule fired. It does not show that a
// requirement is the right one, that its subject is the right element, or that any design meets it.
// The model v0.1 header follows.
// --- generated by the Week 9 lab tool: end ---
// O'Neil "Quick" Relief \ Network */ Co: SysML v2 model v0.1 (Week 8 import of the Systems Thinking package).
// Generated by the Week 8 lab tool on 2026-10-19 from Week 1 model inputs, version 3.
// Course conventions: every Phase I ID is a quoted short name <'ID'>; Context and Stakeholders are modeled now;
// every later package says which week fills it. Check this file with the course-designated checker: a PASS means it
// parsed, every name resolved and no validation rule fired. It does not show the model says what your register says.
// Dependencies: `from` names the dependent element (client), `to` the element it depends on (supplier).
// Left out (defects, fix in the Week 1 record): REL-004.
package 'O\'Neil "Quick" Relief \\ Network */ Co Model' {
	doc /* Purpose: Stress probe of the Week 9 generator; FICTIONAL. */
	private import ScalarValues::*;
	// --- generated by the Week 9 lab tool: begin ---
	private import ISQ::*;
	private import SI::*;
	private import ModelingMetadata::*;
	private import RequirementDerivation::*;
	private import VerificationCases::*;
	// Course convention: a need serves a mission or objective; the dependency runs from the need (client) to what it serves (supplier).
	metadata def <serves> ServesLink {
		doc /* Tags a dependency from a need (client, after from) to the mission or objective it serves (supplier, after to): a change to the objective may require a change to the need. */
		:> annotatedElement : SysML::Dependency;
	}
	// --- generated by the Week 9 lab tool: end ---
	// --- generated by the Week 10 lab tool: begin ---
	// Course convention: a function or requirement depends on the capability it was derived from; the dependency runs from the dependent element (client) to the capability (supplier).
	metadata def <derivedFrom> DerivedFromLink {
		doc /* Tags a dependency from a function or a requirement (client, after from) to the capability it was derived from in Phase I (supplier, after to): a change to the capability may require a change to the client. A derivation connection cannot be used, because its ends must be requirements and a capability is an action definition. */
		:> annotatedElement : SysML::Dependency;
	}
	// --- generated by the Week 10 lab tool: end ---
	// Course convention: the Week 1 register ratings of a stakeholder, as metadata (SysML v2 textual-notation training deck, slides 108-109).
	metadata def StakeholderAssessment {
		attribute influence : Natural;
		attribute influenceReason : String;
	}
	// Course convention: one keyword per Week 1 relationship type, restricted to dependencies (SysML v2 textual-notation training deck, slide 108); each keyword names the client's relation to the supplier.
	metadata def <conflictsWith> ConflictsWithLink {
		doc /* Tags a dependency between two stakeholders that conflict with each other. The relationship is symmetric: from and to keep the register's order, and the direction carries no meaning. */
		:> annotatedElement : SysML::Dependency;
	}
	metadata def <regulatedBy> RegulatedByLink {
		doc /* Tags a dependency between two stakeholders: the client (from) is regulated by the supplier (to), so the client depends on the supplier. The Week 1 register states it the other way round: supplier regulates client. */
		:> annotatedElement : SysML::Dependency;
	}
	metadata def <coordinatesWith> CoordinatesWithLink {
		doc /* Tags a dependency between two stakeholders that coordinate with each other. The relationship is symmetric: from and to keep the register's order, and the direction carries no meaning. */
		:> annotatedElement : SysML::Dependency;
	}
	package Context {
		doc /* The enterprise, the external systems and the operating context of the system of interest (Week 1). */
		part def <'ENT-001'> 'O\'Neil "Quick" Relief \\ Network */ Co' {
			doc /* Domain: Food security and logistics. Problem: Donated food reaches partner pantries unevenly across the county, so fresh produce runs out early while surplus spoils in store back rooms. Mission (MGO-001, modeled in Week 9): Collect surplus food from donors and deliver it safely to partner pantries across the county every week. */
			// --- generated by the Week 9 lab tool: begin ---
			// Quantities the requirements constrain (Week 9; stakeholder requirements).
			attribute daysWithProduceUntilClosingPercent : Real;
			attribute maxFoodTemperature : ThermodynamicTemperatureValue;
			attribute shortOrdersWithoutNotice : Natural;
			attribute freezerAlarmTime : DurationValue;
			attribute shiftDurationP95 : DurationValue;
			attribute resultValue : Natural;
			// --- generated by the Week 9 lab tool: end ---
		}
		part def 'Public';
		part def 'part';
		part def 'External system EXT-003';
		part def 'context';
		part def 'Physical';
		part def 'weather';
		part context2 {
			doc /* The operating context: the system of interest and 6 external system(s). */
			ref part systemOfInterest :> 'O\'Neil "Quick" Relief \\ Network */ Co Model'::Physical::soi2;
			part <'EXT-001'> public_ : 'Public' { doc /* Public. Kind: actor. Crosses the boundary: surplus food (in). */ }
			part <'EXT-002'> part_ : 'part' { doc /* part. Kind: actor. Crosses the boundary: inspection results and permits (in and out). */ }
			part <'EXT-003'> ext003 : 'External system EXT-003' { doc /* Kind: actor. Crosses the boundary: food deliveries and demand reports (in and out). */ }
			part <'EXT-004'> context3 : 'context' { doc /* context. Kind: actor. Crosses the boundary: shared stock and guidance (in and out). */ }
			part <'EXT-005'> physical : 'Physical' { doc /* Physical. Kind: system. Crosses the boundary: delivery routes and travel times (in). */ }
			part <'EXT-006'> weather2 : 'weather' { doc /* weather. Kind: actor. Crosses the boundary: power for cold storage (in). */ }
		}
	}
	package Stakeholders {
		doc /* Stakeholders as part definitions (the types of stakeholder parameters); concerns with a subject and stakeholders; relationships as tagged dependencies (Week 1 register). */
		part def <'STK-001'> 'Families who say "it\'s */ late"' {
			doc /* Role: user. Main life-cycle stage: Operation. Side: external. Approving authority: no. */
			@StakeholderAssessment { influence = 2; influenceReason = "little leverage alone, but they decide demand"; }
		}
		part def <'STK-002'> 'Volunteer drivers' {
			doc /* Role: authority. Main life-cycle stage: Concept. Side: external. Approving authority: yes. */
			@StakeholderAssessment { influence = 5; influenceReason = "it can suspend the food permit"; }
		}
		part def <'STK-003'> 'Grocery store donors' {
			doc /* Role: supplier. Main life-cycle stage: Operation. Side: external. Approving authority: no. */
		}
		part def <'STK-004'> 'Volunteer drivers' {
			doc /* Role: user. Main life-cycle stage: Operation. Side: internal. Approving authority: no. */
			@StakeholderAssessment { influence = 3; influenceReason = "volunteer availability limits deliveries"; }
		}
		part def <'STK-005'> {
			doc /* Role: maintainer. Main life-cycle stage: Logistics and maintenance. Side: internal. Approving authority: no. */
			@StakeholderAssessment { influence = 2; influenceReason = "they keep storage running"; }
		}
		part def <'STK-006'> 'Funders and grant makers' {
			doc /* Role: customer. Main life-cycle stage: Concept. Side: external. Approving authority: no. */
			@StakeholderAssessment { influence = 4; influenceReason = "they fund staff and vans"; }
		}
		part def <'STK-007'> 'Neighbors of the warehouse' {
			doc /* Role: public. Main life-cycle stage: Operation. Side: external. Approving authority: no. */
			@StakeholderAssessment { influence = 2; influenceReason = "they can complain to the zoning board"; }
		}
		part def <'STK-008'> 'Context' {
			doc /* Role: supplier. Main life-cycle stage: Disposal. Side: external. Approving authority: no. */
			@StakeholderAssessment { influence = 2; influenceReason = "disposal costs rise when loads are refused"; }
		}
		concern <'CON-001'> {
			doc /* Families arriving after work find the shelves empty of fresh produce by 5 p.m. */
			subject enterprise : 'O\'Neil "Quick" Relief \\ Network */ Co Model'::Context::'ENT-001';
			stakeholder familiesWhoSayItSLate : 'STK-001';
		}
		concern <'CON-002'> {
			doc /* Cold-chain temperatures above 5 °C during delivery could make donated food unsafe to distribute. */
			subject enterprise : 'O\'Neil "Quick" Relief \\ Network */ Co Model'::Context::'ENT-001';
			stakeholder volunteerDrivers : 'STK-002';
		}
		concern <'CON-003'> {
			doc /* Store managers want surplus collected before closing so it does not fill their back rooms overnight. */
			subject enterprise : 'O\'Neil "Quick" Relief \\ Network */ Co Model'::Context::'ENT-001';
			stakeholder groceryStoreDonors : 'STK-003';
		}
		concern <'CON-004'> {
			doc /* Volunteers drop out when delivery shifts run past the two hours they signed up for. */
			subject enterprise : 'O\'Neil "Quick" Relief \\ Network */ Co Model'::Context::'ENT-001';
			stakeholder volunteerDrivers : 'STK-004';
		}
		concern <'CON-005'> {
			doc /* Freezer breakdowns on weekends go unnoticed until Monday and spoil stored meat. */
			subject enterprise : 'O\'Neil "Quick" Relief \\ Network */ Co Model'::Context::'ENT-001';
			stakeholder stk005 : 'STK-005';
		}
		concern <'CON-007'> {
			doc /* Ends with a backslash \ and a terminator * / inside. */
			subject enterprise : 'O\'Neil "Quick" Relief \\ Network */ Co Model'::Context::'ENT-001';
			stakeholder neighborsOfTheWarehouse : 'STK-007';
		}
		concern <'CON-008'> {
			doc /* Spoiled food mixed with packaging is refused at the composting site. */
			subject enterprise : 'O\'Neil "Quick" Relief \\ Network */ Co Model'::Context::'ENT-001';
			stakeholder context : 'STK-008';
		}
		#conflictsWith dependency <'REL-001'> from 'STK-007' to 'STK-004' {
			doc /* STK-007 conflicts with STK-004. Neighbors want no loading before 6 a.m.; volunteer drivers need early starts to finish within their shifts. */
		}
		#regulatedBy dependency <'REL-002'> from 'STK-005' to 'STK-002' {
			doc /* Register: STK-002 regulates STK-005; modeled from the dependent: STK-005 is regulated by STK-002. Food-safety inspections of the warehouse and cold storage. */
		}
		#coordinatesWith dependency <'REL-003'> from 'STK-004' to 'STK-005' {
			doc /* STK-004 coordinates with STK-005. Loading times at the warehouse dock. */
		}
		dependency <'REL-005'> from 'STK-003' to 'STK-006' {
			doc /* No type chosen. */
		}
	}
	package Needs {
		doc /* The mission, the objectives and the stakeholder needs as requirement usages (Week 9). A need is not a requirement on the system: it states what a stakeholder needs, in the stakeholder's words; course convention: it is modeled as a requirement usage whose subject is the enterprise, with a stakeholder parameter and a frame for each concern it answers. Capabilities follow in Week 10. */
		requirement <'MGO-001'> 'Mission' {
			doc /* Collect surplus food from donors and deliver it safely to partner pantries across the county every week. Level: mission. */
			subject enterprise : 'O\'Neil "Quick" Relief \\ Network */ Co Model'::Context::'ENT-001';
		}
		requirement <'MGO-002'> {
			doc /* Keep partner pantries stocked with fresh food every week. Level: objective. */
			subject enterprise : 'O\'Neil "Quick" Relief \\ Network */ Co Model'::Context::'ENT-001';
		}
		requirement <'MGO-003'> {
			doc /* Keep all donated food safe from collection to delivery. Level: objective. */
			subject enterprise : 'O\'Neil "Quick" Relief \\ Network */ Co Model'::Context::'ENT-001';
		}
		requirement <'MGO-004'> {
			doc /* Run the service within what donors, volunteers and neighbors can sustain. Level: objective. */
			subject enterprise : 'O\'Neil "Quick" Relief \\ Network */ Co Model'::Context::'ENT-001';
		}
		requirement <'MGO-005'> {
			doc /* Show funders how far every delivered pound reaches. Level: objective. */
			subject enterprise : 'O\'Neil "Quick" Relief \\ Network */ Co Model'::Context::'ENT-001';
		}
		requirement <'NEED-001'> 'Requirements' {
			doc /* Families using partner pantries need the delivery service to keep fresh produce on the pantry shelves until closing time. Rationale: Families arriving after work currently find no produce left. Priority: critical. */
			subject enterprise : 'O\'Neil "Quick" Relief \\ Network */ Co Model'::Context::'ENT-001';
			stakeholder familiesUsingPartnerPantries : 'O\'Neil "Quick" Relief \\ Network */ Co Model'::Stakeholders::'STK-001';
			frame 'O\'Neil "Quick" Relief \\ Network */ Co Model'::Stakeholders::'CON-001';
		}
		requirement <'NEED-002'> 'Stakeholders' {
			doc /* The county health department needs the network to keep donated food within safe temperature limits throughout collection, storage and delivery. Rationale: Unsafe temperatures could make distributed food harmful. Priority: mandatory. */
			subject enterprise : 'O\'Neil "Quick" Relief \\ Network */ Co Model'::Context::'ENT-001';
			stakeholder countyHealthDepartment : 'O\'Neil "Quick" Relief \\ Network */ Co Model'::Stakeholders::'STK-002';
			frame 'O\'Neil "Quick" Relief \\ Network */ Co Model'::Stakeholders::'CON-002';
		}
		requirement <'NEED-003'> 'Produce until closing' {
			doc /* Grocery store donors need the collection service to collect surplus food at every store before it closes for the night. Rationale: Surplus left overnight fills their storage space. Priority: desirable. */
			subject enterprise : 'O\'Neil "Quick" Relief \\ Network */ Co Model'::Context::'ENT-001';
			stakeholder groceryStoreDonors : 'O\'Neil "Quick" Relief \\ Network */ Co Model'::Stakeholders::'STK-003';
			frame 'O\'Neil "Quick" Relief \\ Network */ Co Model'::Stakeholders::'CON-003';
		}
		requirement <'NEED-004'> 'Shifts within commitment' {
			doc /* Volunteer drivers need the delivery service to end each delivery shift within the two hours they signed up for, even when donations are heavy. Rationale: Volunteers drop out when shifts overrun their commitment. Priority: critical. */
			subject enterprise : 'O\'Neil "Quick" Relief \\ Network */ Co Model'::Context::'ENT-001';
			stakeholder volunteerDrivers : 'O\'Neil "Quick" Relief \\ Network */ Co Model'::Stakeholders::'STK-004';
			frame 'O\'Neil "Quick" Relief \\ Network */ Co Model'::Stakeholders::'CON-004';
		}
		requirement <'NEED-005'> 'Early warning of storage failure' {
			doc /* Warehouse staff need the "network" to warn them * / within minutes \ at any hour. Rationale: Weekend failures currently spoil stored meat before anyone notices. Priority: critical. */
			subject enterprise : 'O\'Neil "Quick" Relief \\ Network */ Co Model'::Context::'ENT-001';
			stakeholder warehouseStaff : 'O\'Neil "Quick" Relief \\ Network */ Co Model'::Stakeholders::'STK-005';
			frame 'O\'Neil "Quick" Relief \\ Network */ Co Model'::Stakeholders::'CON-005';
		}
		requirement <'NEED-006'> 'Reach by district' {
			doc /* Funders need the network to show how much food reached each county district during every quarter. Rationale: Grant renewals depend on evidence of reach across districts. Priority: desirable. */
			subject enterprise : 'O\'Neil "Quick" Relief \\ Network */ Co Model'::Context::'ENT-001';
			stakeholder fundersAndGrantMakers : 'O\'Neil "Quick" Relief \\ Network */ Co Model'::Stakeholders::'STK-006';
		}
		requirement <'NEED-007'> 'Quiet early mornings' {
			doc /* Neighbors of the warehouse need the delivery service to keep loading noise within the limits agreed with the city, at night and early in the morning. Rationale: Early loading currently wakes residents on Mill Street. Priority: mandatory. */
			subject enterprise : 'O\'Neil "Quick" Relief \\ Network */ Co Model'::Context::'ENT-001';
			stakeholder neighborsOfTheWarehouse : 'O\'Neil "Quick" Relief \\ Network */ Co Model'::Stakeholders::'STK-007';
			frame 'O\'Neil "Quick" Relief \\ Network */ Co Model'::Stakeholders::'CON-007';
		}
		requirement <'NEED-008'> 'Separated spoiled food' {
			doc /* The waste hauler needs the network to separate spoiled food from packaging whenever a load is handed over for composting. Rationale: Mixed loads are refused at the composting site. Priority: optional. */
			subject enterprise : 'O\'Neil "Quick" Relief \\ Network */ Co Model'::Context::'ENT-001';
			stakeholder wasteHauler : 'O\'Neil "Quick" Relief \\ Network */ Co Model'::Stakeholders::'STK-008';
			frame 'O\'Neil "Quick" Relief \\ Network */ Co Model'::Stakeholders::'CON-008';
		}
		requirement <'NEED-009'> 'Shortfall notice' {
			doc /* Pantry coordinators need the delivery service to tell them of any shortfall in their order before the delivery leaves the warehouse. Priority: desirable. */
			subject enterprise : 'O\'Neil "Quick" Relief \\ Network */ Co Model'::Context::'ENT-001';
		}
		#serves dependency 'NEED-001 serves MGO-002' from 'NEED-001' to 'MGO-002';
		#serves dependency 'NEED-002 serves MGO-003' from 'NEED-002' to 'MGO-003';
		#serves dependency 'NEED-003 serves MGO-004' from 'NEED-003' to 'MGO-004';
		#serves dependency 'NEED-004 serves MGO-004' from 'NEED-004' to 'MGO-004';
		#serves dependency 'NEED-005 serves MGO-003' from 'NEED-005' to 'MGO-003';
		#serves dependency 'NEED-006 serves MGO-005' from 'NEED-006' to 'MGO-005';
		#serves dependency 'NEED-007 serves MGO-004' from 'NEED-007' to 'MGO-004';
		#serves dependency 'NEED-008 serves MGO-003' from 'NEED-008' to 'MGO-003';
		#serves dependency 'NEED-009 serves MGO-002' from 'NEED-009' to 'MGO-002';
	}
	package Requirements {
		doc /* The stakeholder and system requirements (Week 9): each with its ID as short name, its statement as doc, a subject, a required constraint where formalized, its attributes and rationale as metadata, and a derivation connection from each parent need or requirement. Parent links to capabilities wait for Week 10, when the capabilities are modeled: REQ-STK-001 to CAP-001; REQ-STK-002 to CAP-002; REQ-STK-003 to CAP-001; REQ-STK-005 to CAP-004; REQ-STK-006 to CAP-005; REQ-SYS-002 to CAP-004. */
		// --- generated by the Week 10 lab tool: begin ---
		// Week 10: these capability links are written in the Logical package as #derivedFrom dependencies (a derivation connection cannot end on a capability, which is an action definition).
		// --- generated by the Week 10 lab tool: end ---
		// Course convention: the Week 2 requirement attributes as metadata (SysML v2 textual-notation training deck, slides 108-109).
		metadata def RequirementAttributes {
			attribute level : String;
			attribute requirementType : String;
			attribute method : VerificationMethodKind;
			attribute criterion : String;
		}
		requirement def DurationUpperLimit {
			doc /* Shared form (course convention): the measured duration shall be at most the limit. Used by REQ-SYS-001, REQ-SYS-002. */
			attribute measured : DurationValue;
			attribute limit : DurationValue;
			require constraint { measured <= limit }
		}
		requirement <'REQ-STK-001'> 'Needs' {
			doc /* The delivery service shall keep fresh produce on the shelves of each partner pantry until at least 30 minutes before its closing time on every distribution day. */
			subject enterprise : 'O\'Neil "Quick" Relief \\ Network */ Co Model'::Context::'ENT-001';
			attribute minDaysWithProduceUntilClosingPercent : Real = 90;
			require constraint { enterprise.daysWithProduceUntilClosingPercent >= minDaysWithProduceUntilClosingPercent }
			@RequirementAttributes { level = "stakeholder"; requirementType = "performance"; method = VerificationMethodKind::analyze; criterion = "Produce on the shelf 30 min before closing on at least 90 % of distribution days, from the pantry closing reports"; }
			@Rationale { text = "Families arriving after work currently find nothing left; the margin covers the last arrivals that coordinators report."; }
		}
		requirement <'REQ-STK-002'> 'Shortfall notice' {
			doc /* The network shall keep donated food at or below 5 °C from collection to delivery. */
			subject enterprise : 'O\'Neil "Quick" Relief \\ Network */ Co Model'::Context::'ENT-001';
			attribute maxFoodTemperatureLimit : ThermodynamicTemperatureValue = 5 ['°C'];
			require constraint { enterprise.maxFoodTemperature <= maxFoodTemperatureLimit }
			@RequirementAttributes { level = "stakeholder"; requirementType = "constraint"; method = VerificationMethodKind::test; criterion = "Logged temperature <= 5 °C for every reading of every load"; }
			@Rationale { text = "The county health department sets this limit in the food permit; an exceedance can suspend all distribution."; }
		}
		requirement <'REQ-STK-003'> 'Shortfall notice (REQ-STK-003)' {
			doc /* The delivery service shall notify the pantry coordinator of any shortfall in an order before the delivery leaves the warehouse. */
			subject enterprise : 'O\'Neil "Quick" Relief \\ Network */ Co Model'::Context::'ENT-001';
			attribute requiredShortOrdersWithoutNotice : Natural = 0;
			require constraint { enterprise.shortOrdersWithoutNotice == requiredShortOrdersWithoutNotice }
			@RequirementAttributes { level = "stakeholder"; requirementType = "functional"; method = VerificationMethodKind::demo; criterion = "Shortfall notice received before departure in every demonstrated short order"; }
			@Rationale { text = "Coordinators plan their distribution around the delivered quantities; a late surprise leaves families without the expected items."; }
		}
		requirement <'REQ-STK-004'> 'Freezer alarm time' {
			doc /* The network shall alert the on-call warehouse staff to a freezer temperature above the alarm limit (TBD-01) within 5 minutes, at any hour. */
			subject enterprise : 'O\'Neil "Quick" Relief \\ Network */ Co Model'::Context::'ENT-001';
			attribute maxFreezerAlarmTime : DurationValue = 5 [min];
			require constraint { enterprise.freezerAlarmTime <= maxFreezerAlarmTime }
			@RequirementAttributes { level = "stakeholder"; requirementType = "performance"; method = VerificationMethodKind::test; criterion = "Alarm received by the on-call phone <= 5 min after an injected rise above TBD-01, in every trial (limit pending U-001)"; }
			@Rationale { text = "Weekend failures currently spoil stored meat before anyone notices; five minutes leaves time to move stock before it warms."; }
			@StatusInfo { status = StatusKind::tbd; owner = "Warehouse manager"; }
		}
		requirement <'REQ-STK-005'> 'Shift length' {
			doc /* The delivery service shall end every volunteer delivery shift within 2 hours of its start. */
			subject enterprise : 'O\'Neil "Quick" Relief \\ Network */ Co Model'::Context::'ENT-001';
			attribute maxShiftDurationP95 : DurationValue = 2 [h];
			require constraint { enterprise.shiftDurationP95 <= maxShiftDurationP95 }
			@RequirementAttributes { level = "stakeholder"; requirementType = "performance"; method = VerificationMethodKind::analyze; criterion = "Shift end minus start <= 2 h for at least 95 % of shifts in a month, from the sign-out log"; }
			@Rationale { text = "Volunteers sign up for two-hour commitments and drop out when they overrun; dispatchers plan against that commitment."; }
		}
		requirement <'REQ-STK-006'> 'Reach report to funders' {
			doc /* The network shall provide the delivered weight per district (TBD-07) to each funder every quarter; "quoted" * / text. */
			subject enterprise : 'O\'Neil "Quick" Relief \\ Network */ Co Model'::Context::'ENT-001';
			attribute maxResultValue : Natural { doc /* TBD-07: value pending. */ }
			require constraint { enterprise.resultValue <= maxResultValue }
			@RequirementAttributes { level = "stakeholder"; requirementType = "interface"; method = VerificationMethodKind::inspect; criterion = "A district-by-district weight table in each quarterly report for 4 consecutive quarters"; }
			@Rationale { text = "Grant renewals depend on evidence of reach across districts; funders compare districts to decide where to invest next."; }
			@StatusInfo { status = StatusKind::tbd; }
		}
		requirement <'REQ-SYS-001'> 'Freezer sampling interval' : DurationUpperLimit {
			doc /* The temperature monitoring function shall sample each freezer temperature at intervals of no more than 60 s. */
			subject temperatureMonitoring : 'O\'Neil "Quick" Relief \\ Network */ Co Model'::Logical::'Temperature monitoring';
			attribute :>> measured = temperatureMonitoring.sampleInterval;
			attribute :>> limit = 60 [s];
			@RequirementAttributes { level = "system"; requirementType = "performance"; method = VerificationMethodKind::test; criterion = "Interval between logged samples <= 60 s over a 24 h test"; }
			@Rationale { text = "An alert within five minutes needs several readings to confirm a rise and to filter out door openings."; }
		}
		requirement <'REQ-SYS-002'> 'Route fits the shift' : DurationUpperLimit {
			doc /* The routing tool shall plan each delivery route so that its planned duration fits within the driver's shift. */
			subject routingTool : 'O\'Neil "Quick" Relief \\ Network */ Co Model'::Logical::'Routing tool';
			attribute :>> measured = routingTool.plannedRouteDuration;
			attribute :>> limit = 2 [h];
			assume constraint { doc /* The route is planned for one driver on a two-hour shift. */ }
			@RequirementAttributes { level = "system"; requirementType = "functional"; method = VerificationMethodKind::demo; criterion = "Planned duration within the shift for every route in a replayed week of orders"; }
			@Rationale { text = "Routes planned longer than the shift are the main reason shifts overrun, according to the volunteer coordinator."; }
		}
		requirement <'REQ-SYS-003'> 'Van cargo temperature' {
			doc /* The refrigerated vans shall hold their cargo at or below 5 °C for a delivery round of up to 3 hours. */
			subject freezer : 'O\'Neil "Quick" Relief \\ Network */ Co Model'::Physical::'Freezer';
			attribute minTemperatureLimit : ThermodynamicTemperatureValue = -18 ['°C'];
			require constraint { freezer.minTemperature >= minTemperatureLimit }
			@RequirementAttributes { level = "system"; requirementType = "constraint"; method = VerificationMethodKind::test; criterion = "Cargo logger <= 5 °C for every reading over a 3 h loaded test round"; }
			@Rationale { text = "The longest round in the county takes about three hours, including loading and unloading at four pantries."; }
		}
		requirement <'REQ-SYS-004'> 'Funder report export' {
			doc /* The reporting function shall export the delivered weight per district in the funders' spreadsheet template. */
			subject systemOfInterest : 'O\'Neil "Quick" Relief \\ Network */ Co Model'::Physical::'System of interest';
			@RequirementAttributes { level = "system"; requirementType = "interface"; method = VerificationMethodKind::demo; criterion = "The export opens in the funders' template with every district filled, for one sampled quarter"; }
			@Rationale { text = "Funders compile reports from many grantees and accept only their own template; retyping by hand introduces errors."; }
		}
		requirement stakeholderRequirements {
			doc /* Specification group: the 6 stakeholder requirements. They share the enterprise as subject, so the group declares it. */
			subject enterprise : 'O\'Neil "Quick" Relief \\ Network */ Co Model'::Context::'ENT-001';
			require 'REQ-STK-001';
			require 'REQ-STK-002';
			require 'REQ-STK-003';
			require 'REQ-STK-004';
			require 'REQ-STK-005';
			require 'REQ-STK-006';
		}
		requirement systemRequirements {
			doc /* Organizing group: the 4 system requirements. Each keeps its own subject, unbound to a group subject, so the group declares none and cannot be satisfied as a whole: satisfy its members. Binding each member subject to a feature of one group subject (Week 11) would make it satisfiable. */
			require 'REQ-SYS-001';
			require 'REQ-SYS-002';
			require 'REQ-SYS-003';
			require 'REQ-SYS-004';
		}
		#derivation connection 'REQ-STK-001 derives from NEED-001' {
			end #original ::> 'O\'Neil "Quick" Relief \\ Network */ Co Model'::Needs::'NEED-001';
			end #derive ::> 'REQ-STK-001';
		}
		#derivation connection 'REQ-STK-002 derives from NEED-002' {
			end #original ::> 'O\'Neil "Quick" Relief \\ Network */ Co Model'::Needs::'NEED-002';
			end #derive ::> 'REQ-STK-002';
		}
		#derivation connection 'REQ-STK-003 derives from NEED-009' {
			end #original ::> 'O\'Neil "Quick" Relief \\ Network */ Co Model'::Needs::'NEED-009';
			end #derive ::> 'REQ-STK-003';
		}
		#derivation connection 'REQ-STK-004 derives from NEED-005' {
			end #original ::> 'O\'Neil "Quick" Relief \\ Network */ Co Model'::Needs::'NEED-005';
			end #derive ::> 'REQ-STK-004';
		}
		#derivation connection 'REQ-STK-006 derives from NEED-006' {
			end #original ::> 'O\'Neil "Quick" Relief \\ Network */ Co Model'::Needs::'NEED-006';
			end #derive ::> 'REQ-STK-006';
		}
		#derivation connection 'REQ-SYS-001 derives from REQ-STK-004' {
			end #original ::> 'REQ-STK-004';
			end #derive ::> 'REQ-SYS-001';
		}
		#derivation connection 'REQ-SYS-002 derives from REQ-STK-005' {
			end #original ::> 'REQ-STK-005';
			end #derive ::> 'REQ-SYS-002';
		}
		#derivation connection 'REQ-SYS-003 derives from REQ-STK-002' {
			end #original ::> 'REQ-STK-002';
			end #derive ::> 'REQ-SYS-003';
		}
		#derivation connection 'REQ-SYS-004 derives from REQ-STK-006' {
			end #original ::> 'REQ-STK-006';
			end #derive ::> 'REQ-SYS-004';
		}
		// --- generated by the Week 11 lab tool: begin ---
		// Interface requirements of the Week 5 record that model v0.3 did not have (course convention: the interface definition is the subject).
		requirement <'REQ-SYS-005'> 'Failure warning delivery' {
			doc /* The alarm gateway shall deliver each failure warning to the scheduling software over IF-006 within 2 min of detection. */
			subject failureWarningsToTheCoordinator : 'O\'Neil "Quick" Relief \\ Network */ Co Model'::Physical::'Failure warnings to the coordinator';
			@RequirementAttributes { level = "system"; requirementType = "interface"; method = VerificationMethodKind::test; criterion = "every warning received within 2 min in 20 injected failures"; }
			@Rationale { text = "A warning that arrives late cannot save the stock."; }
		}
		#derivation connection 'REQ-SYS-005 derives from REQ-STK-004' {
			end #original ::> 'REQ-STK-004';
			end #derive ::> 'REQ-SYS-005';
		}
		requirement <'REQ-SYS-006'> 'Quarterly upload' {
			doc /* The scheduling software shall upload the quarterly reach report to the county portal over IF-003 within five working days of quarter end. */
			@RequirementAttributes { level = "system"; requirementType = "interface"; method = VerificationMethodKind::demo; criterion = "upload confirmed within five working days"; }
		}
		#derivation connection 'REQ-SYS-006 derives from REQ-SYS-004' {
			end #original ::> 'REQ-SYS-004';
			end #derive ::> 'REQ-SYS-006';
		}
		requirement <'REQ-SYS-007'> 'No client names to the AI service' {
			doc /* The scheduling software shall not send any client name to the OpenAI API over IF-009. */
			@RequirementAttributes { level = "system"; requirementType = "interface"; method = VerificationMethodKind::inspect; criterion = "no client name in 50 logged requests"; }
			@Rationale { text = "Client privacy."; }
		}
		#derivation connection 'REQ-SYS-007 derives from NEED-001' {
			end #original ::> 'O\'Neil "Quick" Relief \\ Network */ Co Model'::Needs::'NEED-001';
			end #derive ::> 'REQ-SYS-007';
		}
		// --- generated by the Week 11 lab tool: end ---
	}
	package Behavior {
		doc /* Week 10 models the scenarios as use cases here, with actions and states. */
		// --- generated by the Week 10 lab tool: begin ---
		// The Week 2 scenarios as use cases: subject the enterprise, an actor for each modeled actor, the success end state as objective.
		use case <'SCN-001'> 'Weekly produce delivery to a pantry' {
			doc /* Trigger: A partner pantry submits its weekly order. Preconditions: The pantry has an agreed delivery day; stock is in cold storage; a driver is signed up for the shift. Failure end state: The delivery is rescheduled, the coordinator is told why, and the food stays in cold storage. Actors not modeled as parts: Pantry coordinator. */
			subject enterprise : 'O\'Neil "Quick" Relief \\ Network */ Co Model'::Context::'ENT-001';
			actor volunteerDrivers : 'O\'Neil "Quick" Relief \\ Network */ Co Model'::Stakeholders::'STK-002';
			objective { doc /* Success: The order is delivered within the shift and its weight is recorded. */ }
		}
		use case <'SCN-002'> 'Requirements' {
			doc /* Trigger: The walk-in freezer temperature rises above its alarm limit during the night. Preconditions: The freezer holds stock; an on-call staff member is on the weekend roster. Failure end state: Stock that was warm too long is quarantined, labeled and reported, so none is distributed. Actors not modeled as parts: On-call warehouse staff member, Electric utility. */
			subject enterprise : 'O\'Neil "Quick" Relief \\ Network */ Co Model'::Context::'ENT-001';
			objective { doc /* Success: All stock is back below the limit with a temperature log showing how long it was warm. */ }
			attribute start2 : Boolean;
			attribute powerCutAffectsWholeDistrict : Boolean;
			attribute if_ : Boolean;
			first start;
			then action merge_ :> 'O\'Neil "Quick" Relief \\ Network */ Co Model'::Logical::'FN-005' { doc /* 1. System: then. */ }
			then decide afterMerge;
				if powerCutAffectsWholeDistrict then a2RecordOutageAnd;
				else merge_2;
			action a2RecordOutageAnd { doc /* A2 (after step 1): A power cut affects the whole district. Record the outage and request a refrigerated truck from the federation. The scenario ends. */ }
			then done;
			action merge_2 { doc /* 2. System: Sends the "alarm" * / to staff \ now. */ }
			then decide afterMerge2;
				if if_ then a3Decide;
				else rejoinAcknowledgeAndTravel;
			action a3Decide { doc /* A3 (after step 2): if. decide. The scenario ends. */ }
			then done;
			merge rejoinAcknowledgeAndTravel;
			then action acknowledgeAndTravel { doc /* 3. On-call warehouse staff member: Acknowledges the alarm and travels to the warehouse. */ }
			then decide afterAcknowledgeAndTravel;
				if start2 then done2;
				else moveStock;
			action done2 { doc /* A1 (after step 3): Nobody acknowledges the alarm within 15 minutes. Escalate the alarm to the warehouse manager. Rejoins at step 3. */ }
			then rejoinAcknowledgeAndTravel;
			action moveStock :> 'O\'Neil "Quick" Relief \\ Network */ Co Model'::Logical::'FN-011' { doc /* 4. On-call warehouse staff member: Moves the stock to the backup freezer and logs the temperatures. */ }
			then done;
		}
		use case <'SCN-003'> 'Refrigerated van maintenance' {
			doc /* Trigger: A van's refrigeration unit reports a fault code after a delivery. Preconditions: The van is back at the warehouse; the repair shop has an account with the network. Failure end state: The van stays marked unavailable and its routes are covered by the other vans. Actors not modeled as parts: Fleet maintenance volunteer, Van repair shop. */
			subject enterprise : 'O\'Neil "Quick" Relief \\ Network */ Co Model'::Context::'ENT-001';
			objective { doc /* Success: The van passes the temperature test and is back on the schedule. */ }
		}
		// The signals that trigger the transitions.
		attribute def TemperatureAboveLimit;
		attribute def TemperatureRestored;
		attribute def StaffArrived;
		attribute def FreezerRepaired;
		state def StateDef {
			doc /* Operating states of the walk-in freezer (SCN-002) */
			attribute backupFreezerAvailable : Boolean;
			first start then cold;
			state cold { doc /* Holding stock below the alarm limit. */ do 'O\'Neil "Quick" Relief \\ Network */ Co Model'::Logical::'FN-005'; }
			state alarmRaised { entry 'O\'Neil "Quick" Relief \\ Network */ Co Model'::Logical::'FN-006'; }
			state stockInBackup { doc /* Stock moved to the backup freezer. */ entry 'O\'Neil "Quick" Relief \\ Network */ Co Model'::Logical::'FN-011'; }
			state quarantine { doc /* Warm stock labeled and held back from distribution. */ }
			state transition_ { doc /* An unreachable state * / with a terminator. */ }
			transition coldToAlarmRaised first cold accept TemperatureAboveLimit then alarmRaised;
			transition alarmRaisedToCold first alarmRaised accept TemperatureRestored then cold;
			transition alarmRaisedToStockInBackup first alarmRaised accept StaffArrived if backupFreezerAvailable then stockInBackup;
			transition alarmRaisedToQuarantine first alarmRaised accept StaffArrived if not backupFreezerAvailable then quarantine;
			transition stockInBackupToCold first stockInBackup accept FreezerRepaired then cold;
			transition quarantineToCold first quarantine accept FreezerRepaired then cold;
		}
		state freezerStates : StateDef;
		// --- generated by the Week 10 lab tool: end ---
	}
	package Logical {
		doc /* Week 10 models the functions and logical elements here. */
		// --- generated by the Week 9 lab tool: begin ---
		part def 'Temperature monitoring' {
			doc /* Placeholder subject of REQ-SYS-001 (Week 9). Week 10 models this element; keep the name, or update the subjects when it is renamed. */
			attribute sampleInterval : DurationValue;
		}
		part def 'Routing tool' {
			doc /* Placeholder subject of REQ-SYS-002 (Week 9). Week 10 models this element; keep the name, or update the subjects when it is renamed. */
			attribute plannedRouteDuration : DurationValue;
		}
		// --- generated by the Week 9 lab tool: end ---
		// --- generated by the Week 10 lab tool: begin ---
		// The capabilities (Week 2) as action definitions (course convention).
		action def <'CAP-001'> 'Logical (CAP-001)' { doc /* Deliver ordered fresh food to every partner pantry on its agreed day. */ }
		action def <'CAP-002'> 'Keep food cold' { doc /* Keep donated food within safe temperatures from collection to delivery. */ }
		action def <'CAP-003'> 'Detect storage failures' { doc /* Detect a storage temperature failure at any hour and bring staff to it. */ }
		action def <'CAP-004'> 'Plan routes within shifts' { doc /* Plan delivery routes that fit the volunteers' committed shift length. */ }
		action def <'CAP-005'> 'Report reach by district (CAP-005)' { doc /* Report how much food reached each county district each quarter. */ }
		// The items the functions consume and produce: the Week 4 information items and the items added in Week 10.
		item def <'INFO-001'> 'action' { doc /* Weekly order lines from each pantry. */ }
		item def <'INFO-002'> 'Delivery records' { doc /* Temperature samples from every freezer. */ }
		item def <'INFO-003'> 'Delivery records (INFO-003)' { doc /* Weight delivered per pantry per run. */ }
		item def <'INFO-004'> 'Van cargo temperature log' { doc /* Cargo temperature over each delivery round. */ }
		item def <'INFO-005'> 'Shift times' { doc /* Each volunteer driver's committed start and end times. */ }
		item def <'INFO-006'> 'Alarm call' { doc /* Information item added in Week 10. */ }
		item def 'Delivery route' { doc /* Information item added in Week 10. */ }
		item def 'Loaded van' { doc /* Material item added in Week 10. */ }
		// The functions (Week 4) as action usages, each with an in parameter for every item it consumes and an out parameter for every item it produces.
		action <'FN-001'> 'Logical' {
			in action_ : 'INFO-001';
			in shiftTimes : 'INFO-005';
			out deliveryRoute : 'Delivery route';
		}
		action <'FN-002'> 'Deliver order to pantry' {
			in action_ : 'INFO-001';
			out loadedVan : 'Loaded van';
		}
		action <'FN-003'> 'Deliver order to pantry (FN-003)' {
			in loadedVan : 'Loaded van';
			in deliveryRoute : 'Delivery route';
			out deliveryRecords : 'INFO-003';
		}
		action <'FN-004'> 'Notify pantry of shortfall';
		action <'FN-005'> 'state' {
			out deliveryRecords : 'INFO-002';
		}
		action <'FN-006'> 'Alert on-call staff' {
			in deliveryRecords : 'INFO-002';
			out alarmCall : 'INFO-006';
		}
		action <'FN-007'> 'Keep van cargo cold' {
			in loadedVan : 'Loaded van';
			out vanCargoTemperatureLog : 'INFO-004';
		}
		action <'FN-008'> 'Store produce at the pantry' {
			in loadedVan : 'Loaded van';
		}
		action <'FN-009'> 'Service refrigeration equipment' {
			in vanCargoTemperatureLog : 'INFO-004';
		}
		action <'FN-010'> 'Report reach by district';
		action <'FN-011'> 'Move stock to the backup freezer' {
			doc /* Move the stock of a failed freezer into the backup freezer and log its temperatures. Function added in Week 10. */
			in alarmCall : 'INFO-006';
		}
		// Course convention: a function or requirement depends on the capability it was derived from (client after from, supplier after to).
		#derivedFrom dependency 'FN-001 derived from CAP-004' from 'FN-001' to 'CAP-004';
		#derivedFrom dependency 'FN-002 derived from CAP-001' from 'FN-002' to 'CAP-001';
		#derivedFrom dependency 'FN-003 derived from CAP-001' from 'FN-003' to 'CAP-001';
		#derivedFrom dependency 'FN-005 derived from CAP-003' from 'FN-005' to 'CAP-003';
		#derivedFrom dependency 'FN-006 derived from CAP-003' from 'FN-006' to 'CAP-003';
		#derivedFrom dependency 'FN-007 derived from CAP-002' from 'FN-007' to 'CAP-002';
		#derivedFrom dependency 'FN-008 derived from CAP-002' from 'FN-008' to 'CAP-002';
		#derivedFrom dependency 'FN-009 derived from CAP-002' from 'FN-009' to 'CAP-002';
		#derivedFrom dependency 'FN-010 derived from CAP-005' from 'FN-010' to 'CAP-005';
		#derivedFrom dependency 'FN-011 derived from CAP-003' from 'FN-011' to 'CAP-003';
		#derivedFrom dependency 'REQ-STK-001 derived from CAP-001' from 'O\'Neil "Quick" Relief \\ Network */ Co Model'::Requirements::'REQ-STK-001' to 'CAP-001';
		#derivedFrom dependency 'REQ-STK-002 derived from CAP-002' from 'O\'Neil "Quick" Relief \\ Network */ Co Model'::Requirements::'REQ-STK-002' to 'CAP-002';
		#derivedFrom dependency 'REQ-STK-003 derived from CAP-001' from 'O\'Neil "Quick" Relief \\ Network */ Co Model'::Requirements::'REQ-STK-003' to 'CAP-001';
		#derivedFrom dependency 'REQ-STK-004 derived from CAP-003' from 'O\'Neil "Quick" Relief \\ Network */ Co Model'::Requirements::'REQ-STK-004' to 'CAP-003';
		#derivedFrom dependency 'REQ-STK-005 derived from CAP-004' from 'O\'Neil "Quick" Relief \\ Network */ Co Model'::Requirements::'REQ-STK-005' to 'CAP-004';
		#derivedFrom dependency 'REQ-STK-006 derived from CAP-005' from 'O\'Neil "Quick" Relief \\ Network */ Co Model'::Requirements::'REQ-STK-006' to 'CAP-005';
		#derivedFrom dependency 'REQ-SYS-002 derived from CAP-004' from 'O\'Neil "Quick" Relief \\ Network */ Co Model'::Requirements::'REQ-SYS-002' to 'CAP-004';
		// Logical elements (Week 4) as part definitions; a Week 9 placeholder linked to one is specialized, so its requirement subjects still conform.
		part def 'Behavior' :> 'Routing tool' { doc /* Plans routes within shifts. */ }
		part def 'Route planning */ "quoted"' { doc /* Loads, moves and keeps cold the food on the road, and keeps the equipment working. */ }
		part def 'Coordination and reporting' { doc /* Tells pantries and funders what was delivered. */ }
		part def 'Cold-storage monitoring' :> 'Temperature monitoring' { doc /* Watches stored food temperatures and raises alarms. */ }
		part def 'Pantry storage' { doc /* Keeps produce cold at the pantries. */ }
		part logicalArchitecture {
			doc /* The logical architecture (Week 4): one part per logical element, each the performer of the functions allocated to it. */
			part <'LOG-001'> behavior : 'Behavior' {
				perform 'O\'Neil "Quick" Relief \\ Network */ Co Model'::Logical::'FN-001';
			}
			part <'LOG-002'> routePlanningQuoted : 'Route planning */ "quoted"' {
				perform 'O\'Neil "Quick" Relief \\ Network */ Co Model'::Logical::'FN-002';
				perform 'O\'Neil "Quick" Relief \\ Network */ Co Model'::Logical::'FN-007';
				perform 'O\'Neil "Quick" Relief \\ Network */ Co Model'::Logical::'FN-009';
			}
			part <'LOG-003'> coordinationAndReporting : 'Coordination and reporting' {
				perform 'O\'Neil "Quick" Relief \\ Network */ Co Model'::Logical::'FN-004';
				perform 'O\'Neil "Quick" Relief \\ Network */ Co Model'::Logical::'FN-010';
			}
			part <'LOG-004'> coldStorageMonitoring : 'Cold-storage monitoring' {
				perform 'O\'Neil "Quick" Relief \\ Network */ Co Model'::Logical::'FN-005';
				perform 'O\'Neil "Quick" Relief \\ Network */ Co Model'::Logical::'FN-006';
				perform 'O\'Neil "Quick" Relief \\ Network */ Co Model'::Logical::'FN-011';
			}
			part <'LOG-005'> pantryStorage : 'Pantry storage' {
				perform 'O\'Neil "Quick" Relief \\ Network */ Co Model'::Logical::'FN-008';
			}
		}
		// Requirements allocated to functions (Week 4): the function is responsible for realizing the intent of the requirement.
		allocate 'O\'Neil "Quick" Relief \\ Network */ Co Model'::Requirements::'REQ-SYS-002' to 'FN-001';
		allocate 'O\'Neil "Quick" Relief \\ Network */ Co Model'::Requirements::'REQ-SYS-001' to 'FN-004';
		allocate 'O\'Neil "Quick" Relief \\ Network */ Co Model'::Requirements::'REQ-SYS-001' to 'FN-005';
		allocate 'O\'Neil "Quick" Relief \\ Network */ Co Model'::Requirements::'REQ-STK-004' to 'FN-006';
		allocate 'O\'Neil "Quick" Relief \\ Network */ Co Model'::Requirements::'REQ-SYS-003' to 'FN-007';
		allocate 'O\'Neil "Quick" Relief \\ Network */ Co Model'::Requirements::'REQ-STK-001' to 'FN-008';
		allocate 'O\'Neil "Quick" Relief \\ Network */ Co Model'::Requirements::'REQ-SYS-004' to 'FN-010';
		// --- generated by the Week 10 lab tool: end ---
	}
	package Physical {
		doc /* The system of interest and the elements inside its boundary (Week 1). Components, ports and interfaces follow in Week 11. */
		part def 'System of interest' { doc /* The network's collection, warehousing and delivery service that moves donated food from donors to partner pantries. */ }
		part def 'soi';
		part def 'warehouse';
		part def 'Donation intake desk';
		part soi2 : 'System of interest' {
			part <'PRT-001'> soi3 : 'soi';
			part <'PRT-003'> warehouse2 : 'warehouse';
			part <'PRT-004'> donationIntakeDesk : 'Donation intake desk';
		}
		// --- generated by the Week 9 lab tool: begin ---
		part def 'Freezer' {
			doc /* Placeholder subject of REQ-SYS-003 (Week 9). Week 11 models this element; keep the name, or update the subjects when it is renamed. */
			attribute minTemperature : ThermodynamicTemperatureValue;
		}
		// --- generated by the Week 9 lab tool: end ---
		// --- generated by the Week 11 lab tool: begin ---
		// Week 11 models here what the package doc announces: the physical elements, their components, ports and interfaces. The part definitions above it are kept as written; the physical elements that stand for them specialize them.
		// The items added in Week 11: what crosses an interface that no item of the model names.
		item def 'action' { doc /* Material item added in Week 11. */ }
		// The physical elements (Week 4) as part definitions; a part definition of the same name is reused, a linked one is specialized, so the requirements whose subject it is still conform.
		part def 'Logical' { doc /* Battery sensors in each freezer and a cellular gateway. */ }
		part def 'Refrigerated vans' { doc /* Vans * / with "quotes" and \ backslashes. */ }
		part def 'Pantry refrigerators' { doc /* One refrigerator at each partner pantry (the Week 3 decision). */ }
		part def 'Scheduling and reporting software' { doc /* The coordinator's cloud scheduling tool with route planning. */ }
		part def 'Warehouse dock and workshop' { doc /* Loading dock, volunteers and the technician's workshop. */ }
		// The components (Week 5) as part definitions.
		part def 'state' { doc /* Collects sensor readings and places alarm calls. Kind: hardware. Week 5 functions: FN-006 (performed by PHY-001 in this model). */ }
		part def 'Freezer sensors' { doc /* Measure each freezer every minute. Kind: hardware. Week 5 functions: FN-005 (performed by PHY-001 in this model). */ }
		part def 'Route planner' { doc /* Plans routes within driver shifts. Kind: software. Week 5 functions: FN-001 (performed by PHY-004 in this model). */ }
		part def 'Reach reporting' { doc /* Builds the quarterly district report. Kind: software. Week 5 functions: FN-010 (performed by PHY-004 in this model). */ }
		// One port definition per interface (course convention): end A uses it, end B its conjugate, so every out item meets an in item.
		port def 'Pick list to the dock port' {
			doc /* The port of Scheduling and reporting software on IF-001; Warehouse dock and workshop uses its conjugate. */
			out item action_ : 'O\'Neil "Quick" Relief \\ Network */ Co Model'::Logical::'INFO-001';
		}
		port def 'Requirements port' {
			doc /* The port of Refrigerated vans on IF-002; Scheduling and reporting software uses its conjugate. */
			out item deliveryRecordsINFO003 : 'O\'Neil "Quick" Relief \\ Network */ Co Model'::Logical::'INFO-003';
		}
		port def 'Cargo log download port' {
			doc /* The port of Refrigerated vans on IF-004; Warehouse dock and workshop uses its conjugate. */
			out item vanCargoTemperatureLog : 'O\'Neil "Quick" Relief \\ Network */ Co Model'::Logical::'INFO-004';
		}
		port def 'Crates to the pantry port' {
			doc /* The port of Refrigerated vans on IF-005; Pantry refrigerators uses its conjugate. */
			in item loadedVan : 'O\'Neil "Quick" Relief \\ Network */ Co Model'::Logical::'Loaded van';
		}
		port def 'Failure warnings to the coordinator port' {
			doc /* The port of Freezer failure prediction on IF-006; Scheduling and reporting software uses its conjugate. */
		}
		// The interfaces (Week 5) as interface definitions: two port ends and a flow for each crossing.
		interface def 'Pick list to the dock' {
			doc /* Information interface IF-001. Medium: printed pick list. Constraint: pick list ready by 7:00 on delivery days. Degraded mode: Printer down: the coordinator reads the order list to the dock by phone. */
			end port schedulingAndReportingSoftware : 'Pick list to the dock port';
			end port warehouseDockAndWorkshop : ~'Pick list to the dock port';
			flow schedulingAndReportingSoftware.action_ to warehouseDockAndWorkshop.action_;
		}
		interface def 'Requirements' {
			doc /* Information interface IF-002. Medium: driver phone app over the cellular network. Protection: authenticate each driver phone; encrypt records in transit. Degraded mode: No signal: the app keeps the records and syncs them at the dock. */
			end port refrigeratedVans : 'Requirements port';
			end port schedulingAndReportingSoftware : ~'Requirements port';
			flow refrigeratedVans.deliveryRecordsINFO003 to schedulingAndReportingSoftware.deliveryRecordsINFO003;
		}
		interface def 'Cargo log download' {
			doc /* Information interface IF-004. Medium: logger cable at the dock. Degraded mode: Logger unreadable: the load is checked with a probe thermometer before it is kept. */
			end port refrigeratedVans : 'Cargo log download port';
			end port warehouseDockAndWorkshop : ~'Cargo log download port';
			flow refrigeratedVans.vanCargoTemperatureLog to warehouseDockAndWorkshop.vanCargoTemperatureLog;
		}
		interface def 'Crates to the pantry' {
			doc /* Physical interface IF-005. Medium: hand trolley at the pantry door. Constraint: crates into the refrigerator within 10 min of arrival. Degraded mode: Pantry closed: the driver returns the crates to the warehouse cold room. */
			end port refrigeratedVans : 'Crates to the pantry port';
			end port pantryRefrigerators : ~'Crates to the pantry port';
			flow pantryRefrigerators.loadedVan to refrigeratedVans.loadedVan;
		}
		interface def 'Failure warnings to the coordinator' {
			doc /* Information interface IF-006. Medium: vendor cloud alert over the cellular network. Protection: separate alarm account; warnings can never silence the threshold alarm. Degraded mode: Warnings missing: the threshold alarm still calls the on-call phone. */
			end port freezerFailurePrediction : 'Failure warnings to the coordinator port';
			end port schedulingAndReportingSoftware : ~'Failure warnings to the coordinator port';
		}
		part physicalArchitecture {
			doc /* The physical architecture (Week 4 physical view, Week 5 components and interfaces): one part per physical element with its components, the ports of its interfaces and the functions it performs; the externals it exchanges with; the interfaces and connections. */
			part <'PHY-001'> logical : 'O\'Neil "Quick" Relief \\ Network */ Co Model'::Physical::'Logical' {
				part <'CMP-001'> state_ : 'O\'Neil "Quick" Relief \\ Network */ Co Model'::Physical::'state';
				part <'CMP-002'> freezerSensors : 'Freezer sensors';
				port toSchedulingAndReportingSoftware : 'Failure warnings to the coordinator port';
				perform 'O\'Neil "Quick" Relief \\ Network */ Co Model'::Logical::'FN-005';
				perform 'O\'Neil "Quick" Relief \\ Network */ Co Model'::Logical::'FN-006';
			}
			part <'PHY-002'> refrigeratedVans : 'Refrigerated vans' {
				port toSchedulingAndReportingSoftware : 'Requirements port';
				port toWarehouseDockAndWorkshop : 'Cargo log download port';
				port toPantryRefrigerators : 'Crates to the pantry port';
				perform 'O\'Neil "Quick" Relief \\ Network */ Co Model'::Logical::'FN-003';
				perform 'O\'Neil "Quick" Relief \\ Network */ Co Model'::Logical::'FN-007';
			}
			part <'PHY-003'> pantryRefrigerators : 'Pantry refrigerators' {
				port toRefrigeratedVans : ~'Crates to the pantry port';
				perform 'O\'Neil "Quick" Relief \\ Network */ Co Model'::Logical::'FN-008';
			}
			part <'PHY-004'> schedulingAndReportingSoftware : 'Scheduling and reporting software' {
				part <'CMP-003'> routePlanner : 'Route planner';
				part <'CMP-004'> reachReporting : 'Reach reporting';
				port toWarehouseDockAndWorkshop : 'Pick list to the dock port';
				port toRefrigeratedVans : ~'Requirements port';
				port toFreezerFailurePrediction : ~'Failure warnings to the coordinator port';
				perform 'O\'Neil "Quick" Relief \\ Network */ Co Model'::Logical::'FN-001';
				perform 'O\'Neil "Quick" Relief \\ Network */ Co Model'::Logical::'FN-004';
				perform 'O\'Neil "Quick" Relief \\ Network */ Co Model'::Logical::'FN-010';
			}
			part <'PHY-005'> warehouseDockAndWorkshop : 'Warehouse dock and workshop' {
				port toSchedulingAndReportingSoftware : ~'Pick list to the dock port';
				port toRefrigeratedVans : ~'Cargo log download port';
				perform 'O\'Neil "Quick" Relief \\ Network */ Co Model'::Logical::'FN-002';
				perform 'O\'Neil "Quick" Relief \\ Network */ Co Model'::Logical::'FN-009';
			}
			interface <'IF-001'> pickListToTheDock : 'Pick list to the dock' connect schedulingAndReportingSoftware.toWarehouseDockAndWorkshop to warehouseDockAndWorkshop.toSchedulingAndReportingSoftware;
			interface <'IF-002'> requirements : 'Requirements' connect refrigeratedVans.toSchedulingAndReportingSoftware to schedulingAndReportingSoftware.toRefrigeratedVans;
			interface <'IF-004'> cargoLogDownload : 'Cargo log download' connect refrigeratedVans.toWarehouseDockAndWorkshop to warehouseDockAndWorkshop.toRefrigeratedVans;
			interface <'IF-005'> cratesToThePantry : 'Crates to the pantry' connect refrigeratedVans.toPantryRefrigerators to pantryRefrigerators.toRefrigeratedVans;
			interface <'IF-006'> failureWarningsToTheCoordinator : 'Failure warnings to the coordinator' connect logical.toSchedulingAndReportingSoftware to schedulingAndReportingSoftware.toFreezerFailurePrediction;
			connection <'IF-010'> partnerDeliveryAgreement connect warehouseDockAndWorkshop to pantryRefrigerators {
				doc /* Organizational interface IF-010: Partner delivery agreement. Agreement: signed partner pantry agreement. Nothing flows: it records an agreement between owners. */
			}
		}
		// Requirements allocated this week: interface requirements to their interface and to the function that realizes them; open requirements to physical elements.
		allocate 'O\'Neil "Quick" Relief \\ Network */ Co Model'::Requirements::'REQ-SYS-005' to physicalArchitecture.failureWarningsToTheCoordinator;
		allocate 'O\'Neil "Quick" Relief \\ Network */ Co Model'::Requirements::'REQ-SYS-005' to 'O\'Neil "Quick" Relief \\ Network */ Co Model'::Logical::'FN-006';
		allocate 'O\'Neil "Quick" Relief \\ Network */ Co Model'::Requirements::'REQ-STK-001' to physicalArchitecture.pantryRefrigerators;
		// --- generated by the Week 11 lab tool: end ---
	}
	package Verification {
		doc /* Week 12 models the verification cases here. */
	}
	package Analysis {
		doc /* Week 13 models the technologies, the trade study and its decision here. */
	}
	package AROU {
		doc /* Week 13 models the assumptions, risks, opportunities and unknowns here. */
	}
	package Evolution {
		doc /* Week 14 models the roadmap increments here, in a form decided with the instructor. */
	}
}
