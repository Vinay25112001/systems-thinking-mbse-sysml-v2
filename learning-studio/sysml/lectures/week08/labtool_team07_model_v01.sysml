// Riverside Food Bank Network: SysML v2 model v0.1 (Week 8 import of the Systems Thinking package).
// Generated by the Week 8 lab tool on 2026-10-19 from Week 1 model inputs, version 3.
// Course conventions: every Phase I ID is a quoted short name <'ID'>; Context and Stakeholders are modeled now;
// every later package says which week fills it. Check this file with the course-designated checker: a PASS means it
// parsed, every name resolved and no validation rule fired. It does not show the model says what your register says.
// Dependencies: `from` names the dependent element (client), `to` the element it depends on (supplier).
package 'Riverside Food Bank Network Model' {
	doc /* Purpose: Used by the Riverside team and its instructor to trace each delivery, storage and scheduling decision to the stakeholder concern it serves, and to show the health department and funders which concerns each part of the network addresses. */
	private import ScalarValues::*;
	// Course convention: the Week 1 register ratings of a stakeholder, as metadata (SysML v2 textual-notation training deck, slides 108-109).
	metadata def StakeholderAssessment {
		attribute influence : Natural;
		attribute influenceReason : String;
	}
	// Course convention: one keyword per Week 1 relationship type, restricted to dependencies (SysML v2 textual-notation training deck, slide 108); each keyword names the client's relation to the supplier.
	metadata def <conflictsWith> ConflictsWithLink {
		doc /* Tags a dependency between two stakeholders that conflict with each other. The relationship is symmetric: from and to keep the register's order, and the direction carries no meaning. */
		:> annotatedElement : SysML::Dependency;
	}
	metadata def <regulatedBy> RegulatedByLink {
		doc /* Tags a dependency between two stakeholders: the client (from) is regulated by the supplier (to), so the client depends on the supplier. The Week 1 register states it the other way round: supplier regulates client. */
		:> annotatedElement : SysML::Dependency;
	}
	metadata def <coordinatesWith> CoordinatesWithLink {
		doc /* Tags a dependency between two stakeholders that coordinate with each other. The relationship is symmetric: from and to keep the register's order, and the direction carries no meaning. */
		:> annotatedElement : SysML::Dependency;
	}
	package Context {
		doc /* The enterprise, the external systems and the operating context of the system of interest (Week 1). */
		part def <'ENT-001'> 'Riverside Food Bank Network' {
			doc /* Domain: Food security and logistics. Problem: Donated food reaches partner pantries unevenly across the county, so fresh produce runs out early while surplus spoils in store back rooms. Mission (MGO-001, modeled in Week 9): Collect surplus food from donors and deliver it safely to partner pantries across the county every week. */
		}
		part def 'Grocery store donors';
		part def 'County health department';
		part def 'Partner pantries';
		part def 'Regional food bank federation';
		part def 'Road network';
		part def 'Electric utility';
		part context {
			doc /* The operating context: the system of interest and 6 external system(s). */
			ref part systemOfInterest :> Physical::soi;
			part <'EXT-001'> groceryStoreDonors : 'Grocery store donors' { doc /* Grocery store donors. Kind: actor. Crosses the boundary: surplus food (in). */ }
			part <'EXT-002'> countyHealthDepartment : 'County health department' { doc /* County health department. Kind: actor. Crosses the boundary: inspection results and permits (in and out). */ }
			part <'EXT-003'> partnerPantries : 'Partner pantries' { doc /* Partner pantries. Kind: actor. Crosses the boundary: food deliveries and demand reports (in and out). */ }
			part <'EXT-004'> regionalFoodBankFederation : 'Regional food bank federation' { doc /* Regional food bank federation. Kind: actor. Crosses the boundary: shared stock and guidance (in and out). */ }
			part <'EXT-005'> roadNetwork : 'Road network' { doc /* Road network. Kind: system. Crosses the boundary: delivery routes and travel times (in). */ }
			part <'EXT-006'> electricUtility : 'Electric utility' { doc /* Electric utility. Kind: actor. Crosses the boundary: power for cold storage (in). */ }
		}
	}
	package Stakeholders {
		doc /* Stakeholders as part definitions (the types of stakeholder parameters); concerns with a subject and stakeholders; relationships as tagged dependencies (Week 1 register). */
		part def <'STK-001'> 'Families using partner pantries' {
			doc /* Role: user. Main life-cycle stage: Operation. Side: external. Approving authority: no. */
			@StakeholderAssessment { influence = 2; influenceReason = "little leverage alone, but they decide demand"; }
		}
		part def <'STK-002'> 'County health department' {
			doc /* Role: authority. Main life-cycle stage: Concept. Side: external. Approving authority: yes. */
			@StakeholderAssessment { influence = 5; influenceReason = "it can suspend the food permit"; }
		}
		part def <'STK-003'> 'Grocery store donors' {
			doc /* Role: supplier. Main life-cycle stage: Operation. Side: external. Approving authority: no. */
			@StakeholderAssessment { influence = 4; influenceReason = "they decide how much is donated"; }
		}
		part def <'STK-004'> 'Volunteer drivers' {
			doc /* Role: user. Main life-cycle stage: Operation. Side: internal. Approving authority: no. */
			@StakeholderAssessment { influence = 3; influenceReason = "volunteer availability limits deliveries"; }
		}
		part def <'STK-005'> 'Warehouse staff' {
			doc /* Role: maintainer. Main life-cycle stage: Logistics and maintenance. Side: internal. Approving authority: no. */
			@StakeholderAssessment { influence = 2; influenceReason = "they keep storage running"; }
		}
		part def <'STK-006'> 'Funders and grant makers' {
			doc /* Role: customer. Main life-cycle stage: Concept. Side: external. Approving authority: no. */
			@StakeholderAssessment { influence = 4; influenceReason = "they fund staff and vans"; }
		}
		part def <'STK-007'> 'Neighbors of the warehouse' {
			doc /* Role: public. Main life-cycle stage: Operation. Side: external. Approving authority: no. */
			@StakeholderAssessment { influence = 2; influenceReason = "they can complain to the zoning board"; }
		}
		part def <'STK-008'> 'Waste hauler' {
			doc /* Role: supplier. Main life-cycle stage: Disposal. Side: external. Approving authority: no. */
			@StakeholderAssessment { influence = 2; influenceReason = "disposal costs rise when loads are refused"; }
		}
		concern <'CON-001'> {
			doc /* Families arriving after work find the shelves empty of fresh produce by 5 p.m. */
			subject enterprise : Context::'ENT-001';
			stakeholder familiesUsingPartnerPantries : 'STK-001';
		}
		concern <'CON-002'> {
			doc /* Cold-chain temperatures above 5 °C during delivery could make donated food unsafe to distribute. */
			subject enterprise : Context::'ENT-001';
			stakeholder countyHealthDepartment : 'STK-002';
		}
		concern <'CON-003'> {
			doc /* Store managers want surplus collected before closing so it does not fill their back rooms overnight. */
			subject enterprise : Context::'ENT-001';
			stakeholder groceryStoreDonors : 'STK-003';
		}
		concern <'CON-004'> {
			doc /* Volunteers drop out when delivery shifts run past the two hours they signed up for. */
			subject enterprise : Context::'ENT-001';
			stakeholder volunteerDrivers : 'STK-004';
		}
		concern <'CON-005'> {
			doc /* Freezer breakdowns on weekends go unnoticed until Monday and spoil stored meat. */
			subject enterprise : Context::'ENT-001';
			stakeholder warehouseStaff : 'STK-005';
		}
		concern <'CON-006'> {
			doc /* Grant reports have to show pounds delivered per county district each quarter. */
			subject enterprise : Context::'ENT-001';
			stakeholder fundersAndGrantMakers : 'STK-006';
		}
		concern <'CON-007'> {
			doc /* Residents on Mill Street are woken by van loading before 6 a.m. */
			subject enterprise : Context::'ENT-001';
			stakeholder neighborsOfTheWarehouse : 'STK-007';
		}
		concern <'CON-008'> {
			doc /* Spoiled food mixed with packaging is refused at the composting site. */
			subject enterprise : Context::'ENT-001';
			stakeholder wasteHauler : 'STK-008';
		}
		#conflictsWith dependency <'REL-001'> from 'STK-007' to 'STK-004' {
			doc /* STK-007 conflicts with STK-004. Neighbors want no loading before 6 a.m.; volunteer drivers need early starts to finish within their shifts. */
		}
		#regulatedBy dependency <'REL-002'> from 'STK-005' to 'STK-002' {
			doc /* Register: STK-002 regulates STK-005; modeled from the dependent: STK-005 is regulated by STK-002. Food-safety inspections of the warehouse and cold storage. */
		}
		#coordinatesWith dependency <'REL-003'> from 'STK-004' to 'STK-005' {
			doc /* STK-004 coordinates with STK-005. Loading times at the warehouse dock. */
		}
	}
	package Needs {
		doc /* Mapped in Week 8, modeled later: Mission and goals MGO-001 to MGO-005 (Week 9: requirement with a subject); Stakeholder need NEED-001 to NEED-008 (Week 9: requirement with stakeholder parameters, framing its concerns). */
	}
	package Requirements {
		doc /* Week 9 models the stakeholder and system requirements here. */
	}
	package Behavior {
		doc /* Week 10 models the scenarios as use cases here, with actions and states. */
	}
	package Logical {
		doc /* Week 10 models the functions and logical elements here. */
	}
	package Physical {
		doc /* The system of interest and the elements inside its boundary (Week 1). Components, ports and interfaces follow in Week 11. */
		part def 'System of interest' { doc /* The network's collection, warehousing and delivery service that moves donated food from donors to partner pantries. */ }
		part def 'Warehouse and cold storage';
		part def 'Delivery vans and volunteer drivers';
		part def 'Volunteer scheduling office';
		part def 'Donation intake desk';
		part soi : 'System of interest' {
			part <'PRT-001'> warehouseAndColdStorage : 'Warehouse and cold storage';
			part <'PRT-002'> deliveryVansAndVolunteerDrivers : 'Delivery vans and volunteer drivers';
			part <'PRT-003'> volunteerSchedulingOffice : 'Volunteer scheduling office';
			part <'PRT-004'> donationIntakeDesk : 'Donation intake desk';
		}
	}
	package Verification {
		doc /* Week 12 models the verification cases here. */
	}
	package Analysis {
		doc /* Week 13 models the technologies, the trade study and its decision here. */
	}
	package AROU {
		doc /* Week 13 models the assumptions, risks, opportunities and unknowns here. */
	}
	package Evolution {
		doc /* Week 14 models the roadmap increments here, in a form decided with the instructor. */
	}
}
