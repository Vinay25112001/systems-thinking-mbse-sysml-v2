// O'Neil "Quick" Relief \ Network */ Co: SysML v2 model v0.1 (Week 8 import of the Systems Thinking package).
// Generated by the Week 8 lab tool on 2026-10-19 from Week 1 model inputs, version 3.
// Course conventions: every Phase I ID is a quoted short name <'ID'>; Context and Stakeholders are modeled now;
// every later package says which week fills it. Check this file with the course-designated checker: a PASS means it
// parsed, every name resolved and no validation rule fired. It does not show the model says what your register says.
// Dependencies: `from` names the dependent element (client), `to` the element it depends on (supplier).
// Left out (defects, fix in the Week 1 record): REL-004.
package 'O\'Neil "Quick" Relief \\ Network */ Co Model' {
	doc /* Purpose: [Write the model purpose here: who uses this model, and for which decisions.] */
	private import ScalarValues::*;
	// Course convention: the Week 1 register ratings of a stakeholder, as metadata (SysML v2 textual-notation training deck, slides 108-109).
	metadata def StakeholderAssessment {
		attribute influence : Natural;
		attribute influenceReason : String;
	}
	// Course convention: one keyword per Week 1 relationship type, restricted to dependencies (SysML v2 textual-notation training deck, slide 108); each keyword names the client's relation to the supplier.
	metadata def <conflictsWith> ConflictsWithLink {
		doc /* Tags a dependency between two stakeholders that conflict with each other. The relationship is symmetric: from and to keep the register's order, and the direction carries no meaning. */
		:> annotatedElement : SysML::Dependency;
	}
	metadata def <regulatedBy> RegulatedByLink {
		doc /* Tags a dependency between two stakeholders: the client (from) is regulated by the supplier (to), so the client depends on the supplier. The Week 1 register states it the other way round: supplier regulates client. */
		:> annotatedElement : SysML::Dependency;
	}
	metadata def <coordinatesWith> CoordinatesWithLink {
		doc /* Tags a dependency between two stakeholders that coordinate with each other. The relationship is symmetric: from and to keep the register's order, and the direction carries no meaning. */
		:> annotatedElement : SysML::Dependency;
	}
	package Context {
		doc /* The enterprise, the external systems and the operating context of the system of interest (Week 1). */
		part def <'ENT-001'> 'O\'Neil "Quick" Relief \\ Network */ Co' {
			doc /* Domain: Food security and logistics. Problem: Donated food reaches partner pantries unevenly across the county, so fresh produce runs out early while surplus spoils in store back rooms. Mission (MGO-001, modeled in Week 9): Collect surplus food from donors and deliver it safely to partner pantries across the county every week. */
		}
		part def 'Public';
		part def 'part';
		part def 'External system EXT-003';
		part def 'context';
		part def 'Physical';
		part def 'weather';
		part context2 {
			doc /* The operating context: the system of interest and 6 external system(s). */
			ref part systemOfInterest :> 'O\'Neil "Quick" Relief \\ Network */ Co Model'::Physical::soi2;
			part <'EXT-001'> public_ : 'Public' { doc /* Public. Kind: actor. Crosses the boundary: surplus food (in). */ }
			part <'EXT-002'> part_ : 'part' { doc /* part. Kind: actor. Crosses the boundary: inspection results and permits (in and out). */ }
			part <'EXT-003'> ext003 : 'External system EXT-003' { doc /* Kind: actor. Crosses the boundary: food deliveries and demand reports (in and out). */ }
			part <'EXT-004'> context3 : 'context' { doc /* context. Kind: actor. Crosses the boundary: shared stock and guidance (in and out). */ }
			part <'EXT-005'> physical : 'Physical' { doc /* Physical. Kind: system. Crosses the boundary: delivery routes and travel times (in). */ }
			part <'EXT-006'> weather2 : 'weather' { doc /* weather. Kind: actor. Crosses the boundary: power for cold storage (in). */ }
		}
	}
	package Stakeholders {
		doc /* Stakeholders as part definitions (the types of stakeholder parameters); concerns with a subject and stakeholders; relationships as tagged dependencies (Week 1 register). */
		part def <'STK-001'> 'Families who say "it\'s */ late"' {
			doc /* Role: user. Main life-cycle stage: Operation. Side: external. Approving authority: no. */
			@StakeholderAssessment { influence = 2; influenceReason = "little leverage alone, but they decide demand"; }
		}
		part def <'STK-002'> 'Volunteer drivers' {
			doc /* Role: authority. Main life-cycle stage: Concept. Side: external. Approving authority: yes. */
			@StakeholderAssessment { influence = 5; influenceReason = "it can suspend the food permit"; }
		}
		part def <'STK-003'> 'Grocery store donors' {
			doc /* Role: supplier. Main life-cycle stage: Operation. Side: external. Approving authority: no. */
		}
		part def <'STK-004'> 'Volunteer drivers' {
			doc /* Role: user. Main life-cycle stage: Operation. Side: internal. Approving authority: no. */
			@StakeholderAssessment { influence = 3; influenceReason = "volunteer availability limits deliveries"; }
		}
		part def <'STK-005'> {
			doc /* Role: maintainer. Main life-cycle stage: Logistics and maintenance. Side: internal. Approving authority: no. */
			@StakeholderAssessment { influence = 2; influenceReason = "they keep storage running"; }
		}
		part def <'STK-006'> 'Funders and grant makers' {
			doc /* Role: customer. Main life-cycle stage: Concept. Side: external. Approving authority: no. */
			@StakeholderAssessment { influence = 4; influenceReason = "they fund staff and vans"; }
		}
		part def <'STK-007'> 'Neighbors of the warehouse' {
			doc /* Role: public. Main life-cycle stage: Operation. Side: external. Approving authority: no. */
			@StakeholderAssessment { influence = 2; influenceReason = "they can complain to the zoning board"; }
		}
		part def <'STK-008'> 'Context' {
			doc /* Role: supplier. Main life-cycle stage: Disposal. Side: external. Approving authority: no. */
			@StakeholderAssessment { influence = 2; influenceReason = "disposal costs rise when loads are refused"; }
		}
		concern <'CON-001'> {
			doc /* Families arriving after work find the shelves empty of fresh produce by 5 p.m. */
			subject enterprise : 'O\'Neil "Quick" Relief \\ Network */ Co Model'::Context::'ENT-001';
			stakeholder familiesWhoSayItSLate : 'STK-001';
		}
		concern <'CON-002'> {
			doc /* Cold-chain temperatures above 5 °C during delivery could make donated food unsafe to distribute. */
			subject enterprise : 'O\'Neil "Quick" Relief \\ Network */ Co Model'::Context::'ENT-001';
			stakeholder volunteerDrivers : 'STK-002';
		}
		concern <'CON-003'> {
			doc /* Store managers want surplus collected before closing so it does not fill their back rooms overnight. */
			subject enterprise : 'O\'Neil "Quick" Relief \\ Network */ Co Model'::Context::'ENT-001';
			stakeholder groceryStoreDonors : 'STK-003';
		}
		concern <'CON-004'> {
			doc /* Volunteers drop out when delivery shifts run past the two hours they signed up for. */
			subject enterprise : 'O\'Neil "Quick" Relief \\ Network */ Co Model'::Context::'ENT-001';
			stakeholder volunteerDrivers : 'STK-004';
		}
		concern <'CON-005'> {
			doc /* Freezer breakdowns on weekends go unnoticed until Monday and spoil stored meat. */
			subject enterprise : 'O\'Neil "Quick" Relief \\ Network */ Co Model'::Context::'ENT-001';
			stakeholder stk005 : 'STK-005';
		}
		concern <'CON-007'> {
			doc /* Ends with a backslash \ and a terminator * / inside. */
			subject enterprise : 'O\'Neil "Quick" Relief \\ Network */ Co Model'::Context::'ENT-001';
			stakeholder neighborsOfTheWarehouse : 'STK-007';
		}
		concern <'CON-008'> {
			doc /* Spoiled food mixed with packaging is refused at the composting site. */
			subject enterprise : 'O\'Neil "Quick" Relief \\ Network */ Co Model'::Context::'ENT-001';
			stakeholder context : 'STK-008';
		}
		#conflictsWith dependency <'REL-001'> from 'STK-007' to 'STK-004' {
			doc /* STK-007 conflicts with STK-004. Neighbors want no loading before 6 a.m.; volunteer drivers need early starts to finish within their shifts. */
		}
		#regulatedBy dependency <'REL-002'> from 'STK-005' to 'STK-002' {
			doc /* Register: STK-002 regulates STK-005; modeled from the dependent: STK-005 is regulated by STK-002. Food-safety inspections of the warehouse and cold storage. */
		}
		#coordinatesWith dependency <'REL-003'> from 'STK-004' to 'STK-005' {
			doc /* STK-004 coordinates with STK-005. Loading times at the warehouse dock. */
		}
		dependency <'REL-005'> from 'STK-003' to 'STK-006' {
			doc /* No type chosen. */
		}
	}
	package Needs {
		doc /* Mapped in Week 8, modeled later: Mission and goals MGO-001 to MGO-005 (Week 9: requirement with a subject); Stakeholder need NEED-001 to NEED-008 (Week 9: requirement with stakeholder parameters, framing its concerns). */
	}
	package Requirements {
		doc /* Week 9 models the stakeholder and system requirements here. */
	}
	package Behavior {
		doc /* Week 10 models the scenarios as use cases here, with actions and states. */
	}
	package Logical {
		doc /* Week 10 models the functions and logical elements here. */
	}
	package Physical {
		doc /* The system of interest and the elements inside its boundary (Week 1). Components, ports and interfaces follow in Week 11. */
		part def 'System of interest' { doc /* The network's collection, warehousing and delivery service that moves donated food from donors to partner pantries. */ }
		part def 'soi';
		part def 'warehouse';
		part def 'Donation intake desk';
		part soi2 : 'System of interest' {
			part <'PRT-001'> soi3 : 'soi';
			part <'PRT-003'> warehouse2 : 'warehouse';
			part <'PRT-004'> donationIntakeDesk : 'Donation intake desk';
		}
	}
	package Verification {
		doc /* Week 12 models the verification cases here. */
	}
	package Analysis {
		doc /* Week 13 models the technologies, the trade study and its decision here. */
	}
	package AROU {
		doc /* Week 13 models the assumptions, risks, opportunities and unknowns here. */
	}
	package Evolution {
		doc /* Week 14 models the roadmap increments here, in a form decided with the instructor. */
	}
}
