// AeroLink Urban Mobility: SysML v2 model v0.1 (Week 8 import of the Systems Thinking package).
// Generated by the Week 8 lab tool from the corrected Week 1 AeroLink case and the instructor reference baseline.
// AeroLink Urban Mobility is FICTIONAL: every name, rating and statement is a teaching value (Week 1 case).
// Course conventions: every Phase I ID is a quoted short name <'ID'>; Context and Stakeholders are modeled now;
// every later package says which week fills it. Check this file with the course-designated checker: a PASS means it
// parsed, every name resolved and no validation rule fired. It does not show the model says what your register says.
// Dependencies: `from` names the dependent element (client), `to` the element it depends on (supplier).
package 'AeroLink Model v0.1' {
	doc /* Purpose: The instructor reference model of the AeroLink enterprise (FICTIONAL). It is used by the course team to trace every later requirement, design element and verification case back to the stakeholder concern it serves, and to produce the stakeholder and concern views reviewed in Week 14. */
	private import ScalarValues::*;
	// Course convention: the Week 1 register ratings of a stakeholder, as metadata (SysML v2 textual-notation training deck, slides 108-109).
	metadata def StakeholderAssessment {
		attribute interest : Natural;
		attribute influence : Natural;
		attribute influenceReason : String;
		attribute support : Natural;
		attribute supportReason : String;
	}
	// Course convention: one keyword per Week 1 relationship type, restricted to dependencies (SysML v2 textual-notation training deck, slide 108); each keyword names the client's relation to the supplier.
	metadata def <regulatedBy> RegulatedByLink {
		doc /* Tags a dependency between two stakeholders: the client (from) is regulated by the supplier (to), so the client depends on the supplier. The Week 1 register states it the other way round: supplier regulates client. */
		:> annotatedElement : SysML::Dependency;
	}
	metadata def <conflictsWith> ConflictsWithLink {
		doc /* Tags a dependency between two stakeholders that conflict with each other. The relationship is symmetric: from and to keep the register's order, and the direction carries no meaning. */
		:> annotatedElement : SysML::Dependency;
	}
	metadata def <suppliedBy> SuppliedByLink {
		doc /* Tags a dependency between two stakeholders: the client (from) is supplied by the supplier (to), so the client depends on the supplier. The Week 1 register states it the other way round: supplier supplies client. */
		:> annotatedElement : SysML::Dependency;
	}
	metadata def <fundedBy> FundedByLink {
		doc /* Tags a dependency between two stakeholders: the client (from) is funded by the supplier (to), so the client depends on the supplier. The Week 1 register states it the other way round: supplier funds client. */
		:> annotatedElement : SysML::Dependency;
	}
	metadata def <coordinatesWith> CoordinatesWithLink {
		doc /* Tags a dependency between two stakeholders that coordinate with each other. The relationship is symmetric: from and to keep the register's order, and the direction carries no meaning. */
		:> annotatedElement : SysML::Dependency;
	}
	metadata def <affectedBy> AffectedByLink {
		doc /* Tags a dependency between two stakeholders: the client (from) is affected by the supplier (to), so the client depends on the supplier. */
		:> annotatedElement : SysML::Dependency;
	}
	metadata def <partnersWith> PartnersWithLink {
		doc /* Tags a dependency between two stakeholders that partner with each other. The relationship is symmetric: from and to keep the register's order, and the direction carries no meaning. */
		:> annotatedElement : SysML::Dependency;
	}
	package Context {
		doc /* The enterprise, the external systems and the operating context of the system of interest (Week 1). */
		part def <'ENT-001'> 'AeroLink Urban Mobility' {
			doc /* Domain: Urban air mobility (FICTIONAL) Problem: Cross-town trips in the region take 45-70 minutes by road at peak hours, and no service offers a quick, predictable alternative for trips of 15-40 km (FICTIONAL, proposed). Mission (MGO-001, modeled in Week 9): Safe, quiet, on-demand air trips between six vertiports, at predictable waits and a cost that lets the network grow. */
		}
		part def 'Controlled airspace (air traffic service)';
		part def 'Electric grid';
		part def 'Weather';
		part def 'Aircraft and spares supply';
		part def 'Public transport network';
		part def 'Emergency response service';
		part context {
			doc /* The operating context: the system of interest and 6 external system(s). */
			ref part systemOfInterest :> Physical::soi;
			part <'EXT-001'> controlledAirspaceAirTrafficService : 'Controlled airspace (air traffic service)' { doc /* Controlled airspace (air traffic service). Kind: system. Crosses the boundary: airspace access, clearances and traffic information (in and out). */ }
			part <'EXT-002'> electricGrid : 'Electric grid' { doc /* Electric grid. Kind: system. Crosses the boundary: power to the vertiport chargers (in and out). */ }
			part <'EXT-003'> weather : 'Weather' { doc /* Weather. Kind: system. Crosses the boundary: constrains operations (one-way influence) (in). */ }
			part <'EXT-004'> aircraftAndSparesSupply : 'Aircraft and spares supply' { doc /* Aircraft and spares supply. Kind: system. Crosses the boundary: aircraft and parts; delivery lead time (in and out). */ }
			part <'EXT-005'> publicTransportNetwork : 'Public transport network' { doc /* Public transport network. Kind: system. Crosses the boundary: passengers to and from vertiports (in and out). */ }
			part <'EXT-006'> emergencyResponseService : 'Emergency response service' { doc /* Emergency response service. Kind: system. Crosses the boundary: incident response at vertiports and in flight (in and out). */ }
		}
	}
	package Stakeholders {
		doc /* Stakeholders as part definitions (the types of stakeholder parameters); concerns with a subject and stakeholders; relationships as tagged dependencies (Week 1 register). */
		part def <'STK-001'> 'Passengers' {
			doc /* Role: User or operator. Main life-cycle stage: Operation. Side: external. Approving authority: no. */
			@StakeholderAssessment { interest = 5; influence = 3; influenceReason = "Revenue depends on them, but individually they have little leverage; collectively they decide demand"; support = 2; supportReason = "Curious but unconvinced until the service proves safe, quick and affordable"; }
		}
		part def <'STK-002'> 'FAA' {
			doc /* Role: Approving or regulatory authority. Main life-cycle stage: Concept. Side: external. Approving authority: yes. */
			@StakeholderAssessment { interest = 4; influence = 5; influenceReason = "Approval authority: without it no revenue operation is possible"; support = 2; supportReason = "Neutral by mandate; engaged, but commits only to evidence"; }
		}
		part def <'STK-003'> 'Investors' {
			doc /* Role: Customer, acquirer or funder. Main life-cycle stage: Concept. Side: external. Approving authority: no. */
			@StakeholderAssessment { interest = 4; influence = 5; influenceReason = "Control funding for fleet and vertiport growth"; support = 4; supportReason = "Have committed capital to the venture"; }
		}
		part def <'STK-004'> 'Communities' {
			doc /* Role: Affected public. Main life-cycle stage: Concept. Side: external. Approving authority: no. */
			@StakeholderAssessment { interest = 4; influence = 4; influenceReason = "Local opposition can block vertiport siting through planning processes"; support = 1; supportReason = "Aware of the plan; skeptical about noise near homes"; }
		}
		part def <'STK-005'> 'Vertiport operators' {
			doc /* Role: Supplier or owner of an enabling or external system. Main life-cycle stage: Operation. Side: external. Approving authority: no. */
			@StakeholderAssessment { interest = 5; influence = 4; influenceReason = "Own a scarce capacity constraint (pads, chargers)"; support = 3; supportReason = "Gain traffic from the service; want throughput protected"; }
		}
		part def <'STK-006'> 'Emergency responders' {
			doc /* Role: Supplier or owner of an enabling or external system. Main life-cycle stage: Operation. Side: external. Approving authority: no. */
			@StakeholderAssessment { interest = 3; influence = 3; influenceReason = "Must be able to respond; can impose operating conditions"; support = 2; supportReason = "Understand the plan; battery-fire procedures not yet agreed"; }
		}
		part def <'STK-007'> 'Air navigation service provider' {
			doc /* Role: Approving or regulatory authority. Main life-cycle stage: Operation. Side: external. Approving authority: no. */
			@StakeholderAssessment { interest = 4; influence = 5; influenceReason = "Controls access to airspace; capacity limits schedule density"; support = 2; supportReason = "Engaged; integration procedures still open"; }
		}
		part def <'STK-008'> 'Pilots / remote operators' {
			doc /* Role: User or operator. Main life-cycle stage: Operation. Side: internal. Approving authority: no. */
			@StakeholderAssessment { interest = 5; influence = 3; influenceReason = "Operate every flight; workforce availability limits scaling"; support = 3; supportReason = "Employees who want the service to succeed; wary of workload"; }
		}
		part def <'STK-009'> 'Maintenance technicians' {
			doc /* Role: Maintainer or support. Main life-cycle stage: Logistics and maintenance. Side: internal. Approving authority: no. */
			@StakeholderAssessment { interest = 4; influence = 2; influenceReason = "Turnaround time drives aircraft availability"; support = 3; supportReason = "Employees; support depends on release pressure staying in check"; }
		}
		part def <'STK-010'> 'Electric utility' {
			doc /* Role: Supplier or owner of an enabling or external system. Main life-cycle stage: Operation. Side: external. Approving authority: no. */
			@StakeholderAssessment { interest = 3; influence = 4; influenceReason = "Grid capacity can cap charging throughput"; support = 2; supportReason = "A new load customer; cautious about peak demand"; }
		}
		part def <'STK-011'> 'Aircraft manufacturer (OEM)' {
			doc /* Role: Supplier or owner of an enabling or external system. Main life-cycle stage: Development. Side: external. Approving authority: no. */
			@StakeholderAssessment { interest = 4; influence = 4; influenceReason = "Sole source for aircraft and parts; delivery delays shape fleet growth"; support = 4; supportReason = "AeroLink is a launch customer; committed"; }
		}
		part def <'STK-012'> 'Insurers' {
			doc /* Role: Supplier or owner of an enabling or external system. Main life-cycle stage: Operation. Side: external. Approving authority: no. */
			@StakeholderAssessment { interest = 3; influence = 4; influenceReason = "Premiums and coverage conditions constrain operations"; support = 1; supportReason = "No loss history yet; aware but uncommitted"; }
		}
		part def <'STK-013'> 'City planning authority' {
			doc /* Role: Approving or regulatory authority. Main life-cycle stage: Concept. Side: external. Approving authority: yes. */
			@StakeholderAssessment { interest = 3; influence = 5; influenceReason = "Grants or blocks vertiport sites"; support = 1; supportReason = "Aware of the proposal; awaiting site applications and consultation"; }
		}
		part def <'STK-014'> 'Accessibility advocates' {
			doc /* Role: Affected public. Main life-cycle stage: Concept. Side: external. Approving authority: no. */
			@StakeholderAssessment { interest = 3; influence = 2; influenceReason = "Shape public acceptance and legal compliance expectations"; support = 1; supportReason = "Aware; not yet consulted on boarding design"; }
		}
		part def <'STK-015'> 'Passengers with reduced mobility' {
			doc /* Role: User or operator. Main life-cycle stage: Operation. Side: external. Approving authority: no. */
			@StakeholderAssessment { interest = 5; influence = 2; influenceReason = "Individually little leverage; accessibility expectations and their advocates amplify it"; support = 1; supportReason = "Not yet consulted; will judge the service by whether boarding works for them"; }
		}
		concern <'CON-001'> 'Predictable waiting time' {
			doc /* Passengers judge the service by how long they wait between confirming a ride and boarding, and by whether that wait is predictable. */
			subject enterprise : Context::'ENT-001';
			stakeholder passengers : 'STK-001';
		}
		concern <'CON-002'> 'Personal safety in flight' {
			doc /* Passengers must be confident that every flight is safe before they will use a new mode of transport. */
			subject enterprise : Context::'ENT-001';
			stakeholder passengers : 'STK-001';
		}
		concern <'CON-003'> 'Affordable fare' {
			doc /* Passengers compare the fare with ride-hail and public transport for the same trip. */
			subject enterprise : Context::'ENT-001';
			stakeholder passengers : 'STK-001';
		}
		concern <'CON-004'> 'Airworthiness and operational safety' {
			doc /* The FAA is concerned that aircraft and operations stay within approved safety limits at all times, including in adverse weather. */
			subject enterprise : Context::'ENT-001';
			stakeholder fAA : 'STK-002';
		}
		concern <'CON-005'> 'Return on capital and path to scale' {
			doc /* Investors are concerned that capital spent on aircraft and vertiports produces capacity that is actually used. */
			subject enterprise : Context::'ENT-001';
			stakeholder investors : 'STK-003';
		}
		concern <'CON-006'> 'Pad throughput and charging capacity' {
			doc /* Vertiport operators are concerned that charging and turnaround, not demand, limit how many flights a pad can handle. */
			subject enterprise : Context::'ENT-001';
			stakeholder vertiportOperators : 'STK-005';
		}
		concern <'CON-007'> 'Battery-fire response at vertiports' {
			doc /* Emergency responders are concerned about early warning, access and procedures for a lithium battery fire on a pad. */
			subject enterprise : Context::'ENT-001';
			stakeholder emergencyResponders : 'STK-006';
		}
		concern <'CON-008'> 'Airspace integration' {
			doc /* The air navigation service provider is concerned that air-taxi traffic is known and separated from other airspace users. */
			subject enterprise : Context::'ENT-001';
			stakeholder airNavigationServiceProvider : 'STK-007';
		}
		concern <'CON-009'> 'Operator workload and automation trust' {
			doc /* Pilots and remote operators are concerned about workload, duty time and how far they can trust automated decision aids. */
			subject enterprise : Context::'ENT-001';
			stakeholder pilotsRemoteOperators : 'STK-008';
		}
		concern <'CON-010'> 'Turnaround pressure on maintenance' {
			doc /* Maintenance technicians are concerned that schedule pressure leads to aircraft being released without a clear condition picture. */
			subject enterprise : Context::'ENT-001';
			stakeholder maintenanceTechnicians : 'STK-009';
		}
		concern <'CON-011'> 'Peak grid load' {
			doc /* The electric utility is concerned about simultaneous high-power charging exceeding the agreed connection capacity at a vertiport. */
			subject enterprise : Context::'ENT-001';
			stakeholder electricUtility : 'STK-010';
		}
		concern <'CON-012'> 'Community noise' {
			doc /* Residents near vertiports are concerned about take-off and landing noise, how often it occurs and at what hours. */
			subject enterprise : Context::'ENT-001';
			stakeholder communities : 'STK-004';
		}
		concern <'CON-013'> 'Step-free boarding access' {
			doc /* Accessibility advocates are concerned that passengers using wheelchairs can board and alight without being lifted. */
			subject enterprise : Context::'ENT-001';
			stakeholder accessibilityAdvocates : 'STK-014';
		}
		concern <'CON-014'> 'Quantifiable operational risk' {
			doc /* Insurers are concerned that operational risk is measured and recorded so that premiums can be set on evidence. */
			subject enterprise : Context::'ENT-001';
			stakeholder insurers : 'STK-012';
		}
		concern <'CON-015'> 'Fleet orders and delivery milestones' {
			doc /* The aircraft manufacturer is concerned that AeroLink's aircraft orders, delivery slots and payment milestones are kept as agreed in the purchase agreement, because they set its own production plan. */
			subject enterprise : Context::'ENT-001';
			stakeholder aircraftManufacturerOEM : 'STK-011';
		}
		concern <'CON-016'> 'Land use and zoning of vertiport sites' {
			doc /* The city planning authority is concerned that vertiport sites conform to zoning and land-use plans and connect to public transport, especially sites in residential districts. */
			subject enterprise : Context::'ENT-001';
			stakeholder cityPlanningAuthority : 'STK-013';
		}
		concern <'CON-017'> 'Travel with one\'s own mobility aid' {
			doc /* Passengers with reduced mobility are concerned that they can board, travel and alight without being lifted and without being parted from their wheelchair or other mobility aid. */
			subject enterprise : Context::'ENT-001';
			stakeholder passengersWithReducedMobility : 'STK-015';
		}
		#regulatedBy dependency <'REL-001'> from 'STK-011' to 'STK-002' {
			doc /* Register: STK-002 regulates STK-011; modeled from the dependent: STK-011 is regulated by STK-002. Aircraft certification. */
		}
		#conflictsWith dependency <'REL-002'> from 'STK-004' to 'STK-005' {
			doc /* STK-004 conflicts with STK-005. Noise and siting vs throughput. */
		}
		#suppliedBy dependency <'REL-003'> from 'STK-005' to 'STK-010' {
			doc /* Register: STK-010 supplies STK-005; modeled from the dependent: STK-005 is supplied by STK-010. Grid power for charging. */
		}
		#fundedBy dependency <'REL-004'> from 'STK-011' to 'STK-003' {
			doc /* Register: STK-003 funds STK-011; modeled from the dependent: STK-011 is funded by STK-003. Fleet purchase financing. */
		}
		#coordinatesWith dependency <'REL-005'> from 'STK-006' to 'STK-005' {
			doc /* STK-006 coordinates with STK-005. Incident response plans. */
		}
		#coordinatesWith dependency <'REL-006'> from 'STK-007' to 'STK-008' {
			doc /* STK-007 coordinates with STK-008. Flight clearances. */
		}
		#affectedBy dependency <'REL-007'> from 'STK-013' to 'STK-004' {
			doc /* STK-013 is affected by STK-004. Public consultation on siting. */
		}
		#partnersWith dependency <'REL-008'> from 'STK-012' to 'STK-003' {
			doc /* STK-012 partners with STK-003. Risk transfer conditions on financing. */
		}
	}
	package Needs {
		doc /* Mapped in Week 8, modeled later: Mission and goals MGO-001 to MGO-004, MGO-009 (Week 9: requirement with a subject); Stakeholder need NEED-001 to NEED-017 (Week 9: requirement with stakeholder parameters, framing its concerns); Capability CAP-001 to CAP-010 (Week 10: action def (named; refined in Week 10)). */
	}
	package Requirements {
		doc /* Mapped in Week 8, modeled later: Stakeholder requirement REQ-STK-001 to REQ-STK-010 (Week 9: requirement with a subject, derived from needs); System requirement REQ-SYS-001 to REQ-SYS-010 (Week 9: requirement with a subject, derived from stakeholder requirements). */
	}
	package Behavior {
		doc /* Mapped in Week 8, modeled later: Operational scenario SCN-001 to SCN-005 (Week 10: use case with actors). */
	}
	package Logical {
		doc /* Week 10 models the functions and logical elements here. */
	}
	package Physical {
		doc /* The system of interest and the elements inside its boundary (Week 1). Components, ports and interfaces follow in Week 11. */
		part def 'System of interest' { doc /* the AeroLink air-taxi service: The system of interest inside the enterprise. AeroLink controls the fleet, the operations center, and booking and dispatch: the narrower system of interest. The service also needs elements AeroLink does not control, the vertiport operators' pads and chargers and the passenger demand they serve, so SOI-001 is drawn at the wider system of interest, which SEBoK permits for a service. */ }
		part soi : 'System of interest';
	}
	package Verification {
		doc /* Week 12 models the verification cases here. */
	}
	package Analysis {
		doc /* Week 13 models the technologies, the trade study and its decision here. */
	}
	package AROU {
		doc /* Mapped in Week 8, modeled later: Assumption A-001 to A-008 (Week 13: metadata annotation); Unknown (TBD/TBR) U-001, U-002 (Week 13: metadata annotation). */
	}
	package Evolution {
		doc /* Week 14 models the roadmap increments here, in a form decided with the instructor. */
	}
}
